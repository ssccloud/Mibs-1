HIRSCHMANN-GENERIC-ERROR-MIB   DEFINITIONS ::= BEGIN

-- 
-- ***********************************************************
-- Hirschmann Generic-Error MIB
-- ***********************************************************
--

IMPORTS
    MODULE-IDENTITY, OBJECT-TYPE, OBJECT-IDENTITY, 
	enterprises, Integer32							FROM SNMPv2-SMI
    TEXTUAL-CONVENTION, DisplayString, 
	AutonomousType, TestAndIncr						FROM SNMPv2-TC;

hirschmann					  OBJECT IDENTIFIER ::= { enterprises 248 }
hmMgmtSEEErrorIDGroup 	OBJECT IDENTIFIER ::= { enterprises hirschmann(248) hmManagement(16) 2  }
hmMgmtSEInfoIDGroup 	OBJECT IDENTIFIER ::= { enterprises hirschmann(248) hmManagement(16) 3  }

-- 
-- ***********************************************************
-- hmMgmtSEEErrorIDGroup
-- ***********************************************************
--
hmRedundancyConflict OBJECT-IDENTITY
           STATUS      current
           DESCRIPTION "Conflict Redundancy Protocols: Cannot enable {0} because of enabled {1}."
           ::= { hmMgmtSEEErrorIDGroup 1 }

hmRedundancyConflictPort OBJECT-IDENTITY
           STATUS      current
           DESCRIPTION "Conflict Redundancy Protocols: Cannot enable {0} because of enabled {1} on Ring Port {2}."
           ::= { hmMgmtSEEErrorIDGroup 2 }

hmMaxNumExceeded OBJECT-IDENTITY
           STATUS      current
           DESCRIPTION "Max. number exceeded for {0}."
           ::= { hmMgmtSEEErrorIDGroup 3 }
           
hmAlreadyCreated OBJECT-IDENTITY
           STATUS      current
           DESCRIPTION "Instance already created."
           ::= { hmMgmtSEEErrorIDGroup 4 }
           
hmRedundancyConflictFpgaPort OBJECT-IDENTITY
           STATUS      current
           DESCRIPTION "Conflict Redundancy Protocols: Cannot enable {0} on configured ports."
           ::= { hmMgmtSEEErrorIDGroup 5 }

hmVlanUnawareConflict OBJECT-IDENTITY
           STATUS      current
           DESCRIPTION "Cannot enable {0} because {1} is enabled."
           ::= { hmMgmtSEEErrorIDGroup 6 }

hmRedundancyConflictPortShort OBJECT-IDENTITY
           STATUS      current
           DESCRIPTION "Cannot enable {0} on configured ports. Reason: {1}"
           ::= { hmMgmtSEEErrorIDGroup 7 }
           
-- hmTableFullError - Cannot add more rows to a table.
hmTableFullError OBJECT-IDENTITY
           STATUS      current
           DESCRIPTION "{0} table is full. Maximum allowed: {1}."
           ::= { hmMgmtSEEErrorIDGroup 8 }

hmFunctionNotUsableWithInterface OBJECT-IDENTITY
           STATUS      current
           DESCRIPTION "This function cannot be used with this interface."
           ::= { hmMgmtSEEErrorIDGroup 9 }

-- general conflict 
hmGeneralConflict OBJECT-IDENTITY
           STATUS      current
           DESCRIPTION "{0} conflicts with {1}. {2}."
           ::= { hmMgmtSEEErrorIDGroup 10 }
           
hmGeneralExceededRange OBJECT-IDENTITY
    	STATUS      current
    	DESCRIPTION "The {0} is exceeding the range. Maximum permissable range is {1}..{2}."
    	::= { hmMgmtSEEErrorIDGroup 11 }

-- hmMgmtSEEErrorIDGroup 100 - RMON Group
hmRmonAlarmTableFullErrorReturn OBJECT-IDENTITY
           STATUS      current
           DESCRIPTION "Alarm table full. Only {0} entries are allowed."
           ::= { hmMgmtSEEErrorIDGroup 100 }

-- hmMgmtSEEErrorIDGroup 200 - MGMT Group
hmMgmtUdpPortInUse OBJECT-IDENTITY
           STATUS      current
           DESCRIPTION "Given UDP port is already in use."
           ::= { hmMgmtSEEErrorIDGroup 200 }

hmMgmtTcpPortInUse OBJECT-IDENTITY
           STATUS      current
           DESCRIPTION "Given TCP port is already in use."
           ::= { hmMgmtSEEErrorIDGroup 201 }

hmMgmtIPAddressConflictWithMgmtIP OBJECT-IDENTITY
           STATUS      current
           DESCRIPTION "Given IP address/netmask {0}/{1} conflicts with the management IP address/netmask."
           ::= { hmMgmtSEEErrorIDGroup 202 }
           
hmMgmtIPAddressConflictWithOobIP OBJECT-IDENTITY
           STATUS      current
           DESCRIPTION "Given IP address/netmask {0}/{1} conflicts with the out-of-band management IP address/netmask."
           ::= { hmMgmtSEEErrorIDGroup 203 }
           
hmMgmtIPAddressConflictWithRouterIP OBJECT-IDENTITY
           STATUS      current
           DESCRIPTION "Given IP address/netmask {0}/{1} conflicts with a routing interface IP address/netmask."
           ::= { hmMgmtSEEErrorIDGroup 204 }
           
-- hmMgmtSEEErrorIDGroup 300 - MGMT Group
hm2NetIPAddrInvalid OBJECT-IDENTITY
           STATUS      current
           DESCRIPTION "The {0} IP address is not valid."
           ::= { hmMgmtSEEErrorIDGroup 300 }

hm2NetIPAddrAndGateway OBJECT-IDENTITY
           STATUS      current
           DESCRIPTION "Management IP address and gateway are not on the same subnet."
           ::= { hmMgmtSEEErrorIDGroup 301 }

hm2NetIPAddrAndSubnet OBJECT-IDENTITY
           STATUS      current
           DESCRIPTION "The {0} IP address and subnet mask combination is not valid."
           ::= { hmMgmtSEEErrorIDGroup 302 }

hm2NetPrefixLengthInvalid OBJECT-IDENTITY
           STATUS      current
           DESCRIPTION "Subnet mask must have contiguous ones and be no longer than 30 bits."
           ::= { hmMgmtSEEErrorIDGroup 303 }

hm2VlanIdNotExists OBJECT-IDENTITY
           STATUS      current
           DESCRIPTION "VLAN {0} does not exist. Please create VLAN {1} before using it."
           ::= { hmMgmtSEEErrorIDGroup 304 }

--
-- ***********************************************************
-- hmMgmtSEInfoIDGroup
-- ***********************************************************
--
hmMgmtSEInfoValueChanged OBJECT-IDENTITY
           STATUS      current
           DESCRIPTION "Note: Value changed from {0} to {1}"
           ::= { hmMgmtSEInfoIDGroup 1 }

END
