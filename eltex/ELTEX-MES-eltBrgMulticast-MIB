ELTEX-MES-eltBrgMulticast-MIB DEFINITIONS ::= BEGIN

-- Title:      Eltex MES Multicast Bridge Configuration
-- Version:    1.3
-- Date:       12-Jul-2016

IMPORTS
    InterfaceIndex                                       FROM IF-MIB
    TruthValue,TEXTUAL-CONVENTION,
    RowStatus                                            FROM SNMPv2-TC
    VlanIndex,PortList                                   FROM Q-BRIDGE-MIB
    MODULE-IDENTITY, OBJECT-TYPE                         FROM SNMPv2-SMI
    rlIgmpMldSnoopVlanEntry                              FROM RADLAN-rlMacMulticast-MIB
    eltMesMacMulticast                                   FROM ELTEX-MES
    InetAddress                                          FROM INET-ADDRESS-MIB;

-- mld
eltMesMldSnoop  OBJECT IDENTIFIER ::= { eltMesMacMulticast 5 }
--
-- MulticastFiltering
eltMesMacMulticastFilter OBJECT IDENTIFIER ::= { eltMesMacMulticast 1 }
--
-- MulticastVlanFiltering
eltMesMacMulticastFilterPerVlan OBJECT IDENTIFIER ::= { eltMesMacMulticastFilter 1 }
--

eltIgmpMldSnoopVlanTable OBJECT-TYPE
    SYNTAX      SEQUENCE OF EltIgmpMldSnoopVlanEntry
    MAX-ACCESS  not-accessible
    STATUS      current
    DESCRIPTION
        "The table lists the per vlan parameters."
    ::= { eltMesMldSnoop 5 }

eltIgmpMldSnoopVlanEntry OBJECT-TYPE
    SYNTAX      EltIgmpMldSnoopVlanEntry
    MAX-ACCESS  not-accessible
    STATUS      current
    DESCRIPTION
        "This table augments existing RADLAN table rlIgmpMldSnoopVlanTable"
    AUGMENTS { rlIgmpMldSnoopVlanEntry }
    ::= { eltIgmpMldSnoopVlanTable 1 }

EltIgmpMldSnoopVlanEntry ::= SEQUENCE {
    eltIgmpMldSnoopVlanIsImmediateLeaveHostBased    TruthValue,
    eltIgmpMldSnoopVlanCos                          INTEGER,
    eltIgmpMldSnoopVlanReplaceSourceIp              InetAddress,
    eltIgmpMldSnoopVlanProxyReportEnable            TruthValue,
    eltIgmpMldSnoopVlanProxyReportVersion           INTEGER
}

eltIgmpMldSnoopVlanIsImmediateLeaveHostBased OBJECT-TYPE
    SYNTAX      TruthValue
    MAX-ACCESS  read-write
    STATUS      current
    DESCRIPTION
        "Enable/Disable host based immediate leave on this Vlan"
    DEFVAL {false}
    ::= { eltIgmpMldSnoopVlanEntry 1 }

eltIgmpMldSnoopVlanCos OBJECT-TYPE
    SYNTAX INTEGER (0..7 | 255)
    MAX-ACCESS read-write
    STATUS current
    DESCRIPTION
        "Assign IEEE 802.1p value (0-7) to the IGMP packets in this VLAN.
         Value 255 means CoS will not be change."
    DEFVAL {255}
    ::= { eltIgmpMldSnoopVlanEntry 2 }

eltIgmpMldSnoopVlanReplaceSourceIp OBJECT-TYPE
    SYNTAX InetAddress
    MAX-ACCESS read-write
    STATUS current
    DESCRIPTION
        "Before forwarding the report packet sent by the host, the source IP
         address in the packet will be replaced by this IP address.
         Default value of 0.0.0.0 means that the source IP address will not be
         replaced."
    ::= { eltIgmpMldSnoopVlanEntry 3 }

eltIgmpMldSnoopVlanProxyReportEnable OBJECT-TYPE
    SYNTAX      TruthValue
    MAX-ACCESS  read-write
    STATUS      current
    DESCRIPTION
        "Enable/Disable proxy reporting on the VLAN
         to dynamically control static IGMP groups."
    DEFVAL {false}
    ::= { eltIgmpMldSnoopVlanEntry 4 }

eltIgmpMldSnoopVlanProxyReportVersion OBJECT-TYPE
    SYNTAX      INTEGER (0..3)
    MAX-ACCESS  read-write
    STATUS      current
    DESCRIPTION
        "The version of IGMP which is running on proxy reporting."
    DEFVAL {0}
    ::= { eltIgmpMldSnoopVlanEntry 5 }



-- eltMesMacMulticastUnregFilterPerVlanEnable

eltMacMulticastUnregFilterEnableVlanId1To1024 OBJECT-TYPE
    SYNTAX      OCTET STRING (SIZE(0..128))
    MAX-ACCESS  read-write
    STATUS      current
    DESCRIPTION
        "Each bit represent a VLAN whether Unregistered Multicast Filtering enable "
 ::= { eltMesMacMulticastFilterPerVlan  1 }

eltMacMulticastUnregFilterEnableVlanId1025To2048 OBJECT-TYPE
    SYNTAX      OCTET STRING (SIZE(0..128))
    MAX-ACCESS  read-write
    STATUS      current
    DESCRIPTION
        "Each bit represent a VLAN whether Unregistered Multicast Filtering enable "
 ::= { eltMesMacMulticastFilterPerVlan  2 }
 
eltMacMulticastUnregFilterEnableVlanId2049To3072 OBJECT-TYPE
    SYNTAX      OCTET STRING (SIZE(0..128))
    MAX-ACCESS  read-write
    STATUS      current
    DESCRIPTION
        "Each bit represent a VLAN whether Unregistered Multicast Filtering enable "
 ::= { eltMesMacMulticastFilterPerVlan  3 }
 
eltMacMulticastUnregFilterEnableVlanId3073To4094 OBJECT-TYPE
    SYNTAX      OCTET STRING (SIZE(0..128))
    MAX-ACCESS  read-write
    STATUS      current
    DESCRIPTION
        "Each bit represent a VLAN whether Unregistered Multicast Filtering enable "
 ::= { eltMesMacMulticastFilterPerVlan  4 }

END
