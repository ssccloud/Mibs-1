--  (C) COPYRIGHT HEWLETT-PACKARD COMPANY 2013.
--  
--  HP Officejet Pro X576dw MFP Printer Model Specific MIB.
--  Version - 1.0
--  Generated on Jul. 22, 2013 .
--  
--  Company names and product names mentioned herein may be 
--  trademarks, and/or registered trademarks of their respective
--  companies.
--  
--  This MIB describes all the printer model specific
--  objects supported by the HP Officejet Pro X576dw MFP printer
--  when networked connected.
--  
--  This MIB complies with the following dependencies:
--  
--  Printer-MIB
--  IF-MIB
--  SNMP-FRAMEWORK-MIB
--  IANAifType-MIB
--  INET-ADDRESS-MIB
--  HOST-RESOURCES-MIB
--  IANA-CHARSET-MIB
--  SNMPv2-TC
--  IANA-PRINTER-MIB 

HP-OFFICEJET-PRO-X576DW-MIB             DEFINITIONS        ::=      BEGIN

IMPORTS
	PrtLocalizedDescriptionStringTC ,  PrtMediaUnitTC ,  PrtCapacityUnitTC ,  PrtSubUnitStatusTC ,  PresentOnOff ,  PrtOutputStackingOrderTC ,  PrtOutputPageDeliveryOrientationTC ,  PrtMarkerCounterUnitTC ,  PrtMarkerAddressabilityUnitTC ,  PrtMarkerSuppliesClassTC ,  PrtMarkerSuppliesSupplyUnitTC ,  PrtMarkerColorantRoleTC ,  PrtMediaPathMaxSpeedPrintUnitTC ,  PrtChannelStateTC ,  PrtPrintOrientationTC ,  PrtInterpreterTwoWayTC ,  PrtConsoleDescriptionStringTC ,  PrtAlertSeverityLevelTC
		FROM Printer-MIB
	InterfaceIndex ,  InterfaceIndexOrZero
		FROM IF-MIB
     SnmpAdminString
         FROM SNMP-FRAMEWORK-MIB
	IANAifType
		FROM IANAifType-MIB
	InetAddressType ,  InetAddress ,  InetAddressPrefixLength
		FROM INET-ADDRESS-MIB
	KBytes ,  ProductID
		FROM HOST-RESOURCES-MIB
	IANACharset
		FROM IANA-CHARSET-MIB
	TruthValue ,  DisplayString ,  TimeStamp ,  PhysAddress ,  AutonomousType
		FROM SNMPv2-TC
	PrtGeneralResetTC ,  PrtConsoleDisableTC ,  PrtCoverStatusTC ,  PrtInputTypeTC ,  PrtOutputTypeTC ,  PrtMarkerMarkTechTC ,  PrtMarkerSuppliesTypeTC ,  PrtMediaPathTypeTC ,  PrtChannelTypeTC ,  PrtInterpreterLangFamilyTC ,  PrtConsoleColorTC ,  PrtAlertTrainingLevelTC ,  PrtAlertGroupTC ,  PrtAlertCodeTC
		FROM IANA-PRINTER-MIB
	WEPKeytype
		FROM IEEE802dot11-MIB;
org                                                OBJECT IDENTIFIER               ::= { iso(1)                            3 }
dod                                                OBJECT IDENTIFIER               ::= { org                               6 }
private                                            OBJECT IDENTIFIER               ::= { internet                          4 }
netPMLmgmt                                         OBJECT IDENTIFIER               ::= { netPML                            2 }
netPML                                             OBJECT IDENTIFIER               ::= { netPeripheral                     4 } 
printmib                                           OBJECT IDENTIFIER               ::= { mib-2                            43 }
internet                                           OBJECT IDENTIFIER               ::= { dod                               1 }
enterprises                                        OBJECT IDENTIFIER               ::= { private                           1 }
ieee802dot11                                       OBJECT IDENTIFIER               ::= { 1 2 840 10036 }        
ppmPort                                            OBJECT IDENTIFIER               ::= { ppmMIBObjects                     3 }
ppmPrinter                                         OBJECT IDENTIFIER               ::= { ppmMIBObjects                     2 }
ppmMIB                                             OBJECT IDENTIFIER               ::= { enterprises pwg(2699) mibs(1) ppmMIB(2) }
interface                                          OBJECT IDENTIFIER               ::= { nm                                4 }
consumables                                        OBJECT IDENTIFIER               ::= { print-engine                     10 }
destination-subsystem                              OBJECT IDENTIFIER               ::= { device                            4 }
processing-subsystem                               OBJECT IDENTIFIER               ::= { device                            3 }
source-subsystem                                   OBJECT IDENTIFIER               ::= { device                            2 }
accounting                                         OBJECT IDENTIFIER               ::= { device-system                    16 }
device                                             OBJECT IDENTIFIER               ::= { netPMLmgmt                        1 }
netPeripheral                                      OBJECT IDENTIFIER               ::= { system                            9 }
prtAlert                                           OBJECT IDENTIFIER               ::= { printmib                         18 }
prtConsoleLights                                   OBJECT IDENTIFIER               ::= { printmib                         17 }
prtConsoleDisplayBuffer                            OBJECT IDENTIFIER               ::= { printmib                         16 }
prtInterpreter                                     OBJECT IDENTIFIER               ::= { printmib                         15 }
prtChannel                                         OBJECT IDENTIFIER               ::= { printmib                         14 }
prtMediaPath                                       OBJECT IDENTIFIER               ::= { printmib                         13 }
prtMarkerColorant                                  OBJECT IDENTIFIER               ::= { printmib                         12 }
prtMarkerSupplies                                  OBJECT IDENTIFIER               ::= { printmib                         11 }
prtMarker                                          OBJECT IDENTIFIER               ::= { printmib                         10 }
prtOutput                                          OBJECT IDENTIFIER               ::= { printmib                          9 }
prtInput                                           OBJECT IDENTIFIER               ::= { printmib                          8 }
prtLocalization                                    OBJECT IDENTIFIER               ::= { printmib                          7 }
prtCover                                           OBJECT IDENTIFIER               ::= { printmib                          6 }
prtGeneral                                         OBJECT IDENTIFIER               ::= { printmib                          5 }
hrDevice                                           OBJECT IDENTIFIER               ::= { host                              3 }
at                                                 OBJECT IDENTIFIER               ::= { mib-2                             3 }
mgmt                                               OBJECT IDENTIFIER               ::= { internet                          2 }
hpPrintServer                                      OBJECT IDENTIFIER               ::= { enterprises                      11 }
ieee802dot11i                                      OBJECT IDENTIFIER               ::= { ieee802dot11                      7 }
dot11phy                                           OBJECT IDENTIFIER               ::= { ieee802dot11                      4 }
dot11smt                                           OBJECT IDENTIFIER               ::= { ieee802dot11                      1 }
ppmPortTable                                       OBJECT IDENTIFIER               ::= { ppmPort                           1 }
ppmPrinterTable                                    OBJECT IDENTIFIER               ::= { ppmPrinter                        1 }
ppmMIBObjects                                      OBJECT IDENTIFIER               ::= { ppmMIB                            1 }
snmpAccess                                         OBJECT IDENTIFIER               ::= { nm                               15 }
npSecurityDot11BeaconTable                         OBJECT IDENTIFIER               ::= { npSecurity                       33 }
npSecurityDot11SSIDTable                           OBJECT IDENTIFIER               ::= { npSecurity                        9 }
npNpi                                              OBJECT IDENTIFIER               ::= { npCard                            8 }
npCfgIPAddrTable                                   OBJECT IDENTIFIER               ::= { npCfg                            53 }
npCard                                             OBJECT IDENTIFIER               ::= { interface                         3 }
consumables-1                                      OBJECT IDENTIFIER               ::= { consumables                       1 }
print-engine                                       OBJECT IDENTIFIER               ::= { destination-subsystem             1 }
fax-proc-sub                                       OBJECT IDENTIFIER               ::= { processing-subsystem              7 }
pdl                                                OBJECT IDENTIFIER               ::= { processing-subsystem              3 }
scanner                                            OBJECT IDENTIFIER               ::= { source-subsystem                  2 }
printer-color-accounting                           OBJECT IDENTIFIER               ::= { accounting                        3 }
printer-accounting                                 OBJECT IDENTIFIER               ::= { accounting                        1 }
errorlog                                           OBJECT IDENTIFIER               ::= { device-system                    11 }
device-system                                      OBJECT IDENTIFIER               ::= { device                            1 }
netPrinter                                         OBJECT IDENTIFIER               ::= { netPeripheral                     1 }
prtAlertTable                                      OBJECT IDENTIFIER               ::= { prtAlert                          1 }
prtConsoleLightTable                               OBJECT IDENTIFIER               ::= { prtConsoleLights                  6 }
prtConsoleDisplayBufferTable                       OBJECT IDENTIFIER               ::= { prtConsoleDisplayBuffer           5 }
prtInterpreterTable                                OBJECT IDENTIFIER               ::= { prtInterpreter                    1 }
prtChannelTable                                    OBJECT IDENTIFIER               ::= { prtChannel                        1 }
prtMediaPathTable                                  OBJECT IDENTIFIER               ::= { prtMediaPath                      4 }
prtMarkerColorantTable                             OBJECT IDENTIFIER               ::= { prtMarkerColorant                 1 }
prtMarkerSuppliesTable                             OBJECT IDENTIFIER               ::= { prtMarkerSupplies                 1 }
prtMarkerTable                                     OBJECT IDENTIFIER               ::= { prtMarker                         2 }
prtOutputTable                                     OBJECT IDENTIFIER               ::= { prtOutput                         2 }
prtInputTable                                      OBJECT IDENTIFIER               ::= { prtInput                          2 }
prtLocalizationTable                               OBJECT IDENTIFIER               ::= { prtLocalization                   1 }
prtCoverTable                                      OBJECT IDENTIFIER               ::= { prtCover                          1 }
prtDeviceRefTable                                  OBJECT IDENTIFIER               ::= { prtGeneral                        3 }
prtStorageRefTable                                 OBJECT IDENTIFIER               ::= { prtGeneral                        2 }
prtGeneralTable                                    OBJECT IDENTIFIER               ::= { prtGeneral                        1 }
hrPrinterTable                                     OBJECT IDENTIFIER               ::= { hrDevice                          5 }
hrDeviceTable                                      OBJECT IDENTIFIER               ::= { hrDevice                          2 }
hrStorageTable                                     OBJECT IDENTIFIER               ::= { hrStorage                         3 }
host                                               OBJECT IDENTIFIER               ::= { mib-2                            25 }
udpTable                                           OBJECT IDENTIFIER               ::= { udp                               5 }
tcpConnTable                                       OBJECT IDENTIFIER               ::= { tcp                              13 }
ipNetToMediaTable                                  OBJECT IDENTIFIER               ::= { ip                               22 }
ipRouteTable                                       OBJECT IDENTIFIER               ::= { ip                               21 }
ipAddrTable                                        OBJECT IDENTIFIER               ::= { ip                               20 }
atTable                                            OBJECT IDENTIFIER               ::= { at                                1 }
ifTable                                            OBJECT IDENTIFIER               ::= { interfaces                        2 }
mib-2                                              OBJECT IDENTIFIER               ::= { mgmt                              1 }
nm                                                 OBJECT IDENTIFIER               ::= { hpPrintServer                     2 }
dot11RSNConfigAuthenticationSuitesTable            OBJECT IDENTIFIER               ::= { ieee802dot11i                     3 }
dot11PhyOperationTable                             OBJECT IDENTIFIER               ::= { dot11phy                          1 }
dot11PrivacyTable                                  OBJECT IDENTIFIER               ::= { dot11smt                          5 }
dot11WEPDefaultKeysTable                           OBJECT IDENTIFIER               ::= { dot11smt                          3 }
dot11AuthenticationAlgorithmsTable                 OBJECT IDENTIFIER               ::= { dot11smt                          2 }
dot11StationConfigTable                            OBJECT IDENTIFIER               ::= { dot11smt                          1 }
ppmPortEntry                                       OBJECT IDENTIFIER               ::= { ppmPortTable                      1 }
ppmPrinterEntry                                    OBJECT IDENTIFIER               ::= { ppmPrinterTable                   1 }
ppmGeneral                                         OBJECT IDENTIFIER               ::= { ppmMIBObjects                     1 }
community                                          OBJECT IDENTIFIER               ::= { snmpAccess                        1 }
npSecurityDot11BeaconEntry                         OBJECT IDENTIFIER               ::= { npSecurityDot11BeaconTable        1 }
npSecurityDot11SSIDEntry                           OBJECT IDENTIFIER               ::= { npSecurityDot11SSIDTable          1 }
npSecurity                                         OBJECT IDENTIFIER               ::= { npCard                           20 }
npWeb                                              OBJECT IDENTIFIER               ::= { npCard                           18 }
npPort                                             OBJECT IDENTIFIER               ::= { npCard                           13 }
npIpx                                              OBJECT IDENTIFIER               ::= { npCard                           10 }
npNpiCardAttributeEntry                            OBJECT IDENTIFIER               ::= { npNpi                             4 }
npNpiPeripheralAttributeEntry                      OBJECT IDENTIFIER               ::= { npNpi                             3 }
npCtl                                              OBJECT IDENTIFIER               ::= { npCard                            7 }
npCfgIPAddrEntry                                   OBJECT IDENTIFIER               ::= { npCfgIPAddrTable                  1 }
npCfg                                              OBJECT IDENTIFIER               ::= { npCard                            5 }
npSys                                              OBJECT IDENTIFIER               ::= { npCard                            1 }
consumable-status                                  OBJECT IDENTIFIER               ::= { consumables-1                     1 }
status-prt-eng                                     OBJECT IDENTIFIER               ::= { print-engine                      2 }
status-fax-proc-sub                                OBJECT IDENTIFIER               ::= { fax-proc-sub                      2 }
pdl-postscript                                     OBJECT IDENTIFIER               ::= { pdl                               4 }
pdl-pcl                                            OBJECT IDENTIFIER               ::= { pdl                               3 }
settings-scanner                                   OBJECT IDENTIFIER               ::= { scanner                           1 }
printed-media-color-usage                          OBJECT IDENTIFIER               ::= { printer-color-accounting          1 }
printed-media-usage                                OBJECT IDENTIFIER               ::= { printer-accounting                1 }
error15                                            OBJECT IDENTIFIER               ::= { errorlog                         15 }
error14                                            OBJECT IDENTIFIER               ::= { errorlog                         14 }
error13                                            OBJECT IDENTIFIER               ::= { errorlog                         13 }
error12                                            OBJECT IDENTIFIER               ::= { errorlog                         12 }
error11                                            OBJECT IDENTIFIER               ::= { errorlog                         11 }
error10                                            OBJECT IDENTIFIER               ::= { errorlog                         10 }
error9                                             OBJECT IDENTIFIER               ::= { errorlog                          9 }
error8                                             OBJECT IDENTIFIER               ::= { errorlog                          8 }
error7                                             OBJECT IDENTIFIER               ::= { errorlog                          7 }
error6                                             OBJECT IDENTIFIER               ::= { errorlog                          6 }
error5                                             OBJECT IDENTIFIER               ::= { errorlog                          5 }
error4                                             OBJECT IDENTIFIER               ::= { errorlog                          4 }
error3                                             OBJECT IDENTIFIER               ::= { errorlog                          3 }
error2                                             OBJECT IDENTIFIER               ::= { errorlog                          2 }
error1                                             OBJECT IDENTIFIER               ::= { errorlog                          1 }
test                                               OBJECT IDENTIFIER               ::= { device-system                     5 }
id                                                 OBJECT IDENTIFIER               ::= { device-system                     3 }
status-system                                      OBJECT IDENTIFIER               ::= { device-system                     2 }
settings-system                                    OBJECT IDENTIFIER               ::= { device-system                     1 }
generalDeviceStatus                                OBJECT IDENTIFIER               ::= { netPrinter                        1 }
gdStatusEntry                                      OBJECT IDENTIFIER               ::= { generalDeviceStatus               2 }
prtAlertEntry                                      OBJECT IDENTIFIER               ::= { prtAlertTable                     1 }
prtConsoleLightEntry                               OBJECT IDENTIFIER               ::= { prtConsoleLightTable              1 }
prtConsoleDisplayBufferEntry                       OBJECT IDENTIFIER               ::= { prtConsoleDisplayBufferTable      1 }
prtInterpreterEntry                                OBJECT IDENTIFIER               ::= { prtInterpreterTable               1 }
prtChannelEntry                                    OBJECT IDENTIFIER               ::= { prtChannelTable                   1 }
prtMediaPathEntry                                  OBJECT IDENTIFIER               ::= { prtMediaPathTable                 1 }
prtMarkerColorantEntry                             OBJECT IDENTIFIER               ::= { prtMarkerColorantTable            1 }
prtMarkerSuppliesEntry                             OBJECT IDENTIFIER               ::= { prtMarkerSuppliesTable            1 }
prtMarkerEntry                                     OBJECT IDENTIFIER               ::= { prtMarkerTable                    1 }
prtOutputEntry                                     OBJECT IDENTIFIER               ::= { prtOutputTable                    1 }
prtInputEntry                                      OBJECT IDENTIFIER               ::= { prtInputTable                     1 }
prtLocalizationEntry                               OBJECT IDENTIFIER               ::= { prtLocalizationTable              1 }
prtCoverEntry                                      OBJECT IDENTIFIER               ::= { prtCoverTable                     1 }
prtDeviceRefEntry                                  OBJECT IDENTIFIER               ::= { prtDeviceRefTable                 1 }
prtStorageRefEntry                                 OBJECT IDENTIFIER               ::= { prtStorageRefTable                1 }
prtGeneralEntry                                    OBJECT IDENTIFIER               ::= { prtGeneralTable                   1 }
hrPrinterEntry                                     OBJECT IDENTIFIER               ::= { hrPrinterTable                    1 }
hrDeviceEntry                                      OBJECT IDENTIFIER               ::= { hrDeviceTable                     1 }
hrStorageEntry                                     OBJECT IDENTIFIER               ::= { hrStorageTable                    1 }
hrStorage                                          OBJECT IDENTIFIER               ::= { host                              2 }
hrSystem                                           OBJECT IDENTIFIER               ::= { host                              1 }
snmp                                               OBJECT IDENTIFIER               ::= { mib-2                            11 }
udpEntry                                           OBJECT IDENTIFIER               ::= { udpTable                          1 }
udp                                                OBJECT IDENTIFIER               ::= { mib-2                             7 }
tcpConnEntry                                       OBJECT IDENTIFIER               ::= { tcpConnTable                      1 }
tcp                                                OBJECT IDENTIFIER               ::= { mib-2                             6 }
icmp                                               OBJECT IDENTIFIER               ::= { mib-2                             5 }
ipNetToMediaEntry                                  OBJECT IDENTIFIER               ::= { ipNetToMediaTable                 1 }
ipRouteEntry                                       OBJECT IDENTIFIER               ::= { ipRouteTable                      1 }
ipAddrEntry                                        OBJECT IDENTIFIER               ::= { ipAddrTable                       1 }
ip                                                 OBJECT IDENTIFIER               ::= { mib-2                             4 }
atEntry                                            OBJECT IDENTIFIER               ::= { atTable                           1 }
ifEntry                                            OBJECT IDENTIFIER               ::= { ifTable                           1 }
interfaces                                         OBJECT IDENTIFIER               ::= { mib-2                             2 }
system                                             OBJECT IDENTIFIER               ::= { nm                                3 }
dot11RSNConfigAuthenticationSuitesEntry            OBJECT IDENTIFIER               ::= { dot11RSNConfigAuthenticationSuitesTable    1 }
dot11PhyOperationEntry                             OBJECT IDENTIFIER               ::= { dot11PhyOperationTable            1 }
dot11PrivacyEntry                                  OBJECT IDENTIFIER               ::= { dot11PrivacyTable                 1 }
dot11WEPDefaultKeysEntry                           OBJECT IDENTIFIER               ::= { dot11WEPDefaultKeysTable          1 }
dot11AuthenticationAlgorithmsEntry                 OBJECT IDENTIFIER               ::= { dot11AuthenticationAlgorithmsTable    1 }
dot11StationConfigEntry                            OBJECT IDENTIFIER               ::= { dot11StationConfigTable           1 }
settings-fax-proc-sub                              OBJECT IDENTIFIER               ::= { fax-proc-sub                      1 }

dot11DesiredSSID OBJECT-TYPE
        SYNTAX OCTET STRING (SIZE(0..32))
        MAX-ACCESS read-write
        STATUS current
        DESCRIPTION
        "This attribute reflects the Service Set ID used
        in the DesiredSSID parameter of the most recent
        MLME_Scan.request. This value may be modified
        by an external management entity and used by the
        local SME to make decisions about the Scanning process."
::= { dot11StationConfigEntry 9 }

dot11DesiredBSSType OBJECT-TYPE
        SYNTAX INTEGER { infrastructure(1), independent(2), any(3) }
        MAX-ACCESS read-write
        STATUS current
        DESCRIPTION
        "This attribute shall specify the type of BSS the
        station shall use when scanning for a BSS with which
        to synchronize. This value is used to filter Probe
        Response frames and Beacons. When set to infrastructure,
        the station shall only synchronize with a BSS whose
        Capability Information field has the ESS subfield set
        to 1. When set to independent, the station shall only
        synchronize with a BSS whose Capability Information
        field has the IBSS subfield set to 1. When set to
        any, the station may synchronize to either type of
        BSS."
::= { dot11StationConfigEntry 10 }

dot11AuthenticationAlgorithm OBJECT-TYPE
        SYNTAX INTEGER { openSystem (1), sharedKey (2) }
        MAX-ACCESS read-only
        STATUS current
        DESCRIPTION
        "This attribute shall be a set of all the authentication
        algorithms supported by the STAs. The following are the
        default values and the associated algorithm.
        Value = 1: Open System
        Value = 2: Shared Key"
::= { dot11AuthenticationAlgorithmsEntry 2 }

dot11AuthenticationAlgorithmsEnable OBJECT-TYPE
        SYNTAX TruthValue
        MAX-ACCESS read-write
        STATUS current
        DESCRIPTION
        "This attribute, when true at a station,
        shall enable the acceptance of the authentication
        algorithm described in the corresponding table
        entry in authentication frames received by the
        station that have odd authentication sequence numbers.
        The default value of this attribute shall be 1 for
        the Open System table entry and 2 for all other table entries."
::= { dot11AuthenticationAlgorithmsEntry 3 }

dot11WEPDefaultKeyValue OBJECT-TYPE
        SYNTAX WEPKeytype
        MAX-ACCESS read-write
        STATUS current
        DESCRIPTION
        "A WEP default secret key value."
::= { dot11WEPDefaultKeysEntry 2 }

dot11PrivacyInvoked OBJECT-TYPE
        SYNTAX TruthValue
        MAX-ACCESS read-write
        STATUS current
        DESCRIPTION
        "When this attribute is true, it shall indicate that the IEEE
        802.11 WEP mechanism is used for transmitting frames of type
        Data. The default value of this attribute shall be false."
::= { dot11PrivacyEntry 1 }

dot11WEPDefaultKeyID OBJECT-TYPE
        SYNTAX INTEGER (0..3)
        MAX-ACCESS read-write
        STATUS current
        DESCRIPTION
        "This attribute shall indicate the use of the first,
        second, third, or fourth element of the WEPDefaultKeys
        array when set to values of zero, one, two, or three. The
        default value of this attribute shall be 0."
        REFERENCE "ISO/IEC 8802-11:1999, 8.3.2"
::= { dot11PrivacyEntry 2 }

dot11CurrentRegDomain OBJECT-TYPE
        --   SYNTAX Integer32
        SYNTAX INTEGER {fcc(16),
        doc(32),
        etsi(48),
        spain (49),
        france(50),
        mkk (64),
        japan (65) }
        MAX-ACCESS read-write
        STATUS current
        DESCRIPTION
        "The current regulatory domain this instance of the PMD is
        supporting. This object corresponds to one of the
        RegDomains listed in dot11RegDomainsSupported."
::= { dot11PhyOperationEntry 2 }

dot11RSNConfigAuthenticationSuite OBJECT-TYPE
        SYNTAX		OCTET STRING (SIZE(4))
        MAX-ACCESS	read-only
        STATUS		current
        DESCRIPTION
        "An authentication suite. Note that dot1X and PSK may
        not be enabled simultaneously. These are mutually exclusive.
        The first three octets shall form an OUI and the fourth octet a
        cipher/authentication suite within that OUI space.
        00:00:00:1 is dot1X,
        00:00:00:2 is PSK"
::= { dot11RSNConfigAuthenticationSuitesEntry 2 }

dot11RSNConfigAuthenticationSuiteEnabled OBJECT-TYPE
        SYNTAX		TruthValue
        MAX-ACCESS	read-write
        STATUS		current
        DESCRIPTION
        "This variable indicates whether the corresponding
        authentication suite is enabled/disabled."
::= { dot11RSNConfigAuthenticationSuitesEntry 3 }

--Commenting out the following OID's, since system node from standard MIB file
--clashes with private MIB file.

--sysDescr OBJECT-TYPE
--        SYNTAX  DisplayString (SIZE (0..255))
--        ACCESS  read-only
--        STATUS  mandatory
--        DESCRIPTION
--        "A textual description of the entity.  This value
--        should include the full name and version
--        identification of the system's hardware type,
--        software operating-system, and networking
--        software.  It is mandatory that this only contain
--        printable ASCII characters."
--::= { system 1 }

--sysObjectID OBJECT-TYPE
--        SYNTAX  OBJECT IDENTIFIER
--        ACCESS  read-only
--        STATUS  mandatory
--        DESCRIPTION
--        "The vendor's authoritative identification of the
--        network management subsystem contained in the
--        entity.  This value is allocated within the SMI
--        enterprises subtree (1.3.6.1.4.1) and provides an
--        easy and unambiguous means for determining `what
--        kind of box' is being managed.  For example, if
--        vendor `Flintstones, Inc.' was assigned the
--        subtree 1.3.6.1.4.1.4242, it could assign the
--        identifier 1.3.6.1.4.1.4242.1.1 to its `Fred
--        Router'."
--::= { system 2 }

--sysUpTime OBJECT-TYPE
--        SYNTAX  TimeTicks
--        ACCESS  read-only
--        STATUS  mandatory
--        DESCRIPTION
--        "The time (in hundredths of a second) since the
--        network management portion of the system was last
--        re-initialized."
--::= { system 3 }

--sysContact OBJECT-TYPE
--        SYNTAX  DisplayString (SIZE (0..255))
--        ACCESS  read-write
--        STATUS  mandatory
--        DESCRIPTION
--        "The textual identification of the contact person
--        for this managed node, together with information
--        on how to contact this person."
--::= { system 4 }

--sysName OBJECT-TYPE
--        SYNTAX  DisplayString (SIZE (0..255))
--        ACCESS  read-write
--        STATUS  mandatory
--        DESCRIPTION
--        "An administratively-assigned name for this
--        managed node.  By convention, this is the node's
--        fully-qualified domain name."
--::= { system 5 }

--sysLocation OBJECT-TYPE
--        SYNTAX  DisplayString (SIZE (0..255))
--        ACCESS  read-write
--        STATUS  mandatory
--        DESCRIPTION
--        "The physical location of this node (e.g.,
--        `telephone closet, 3rd floor')."
--::= { system 6 }

--sysServices OBJECT-TYPE
--        SYNTAX  INTEGER (0..127)
--        ACCESS  read-only
--        STATUS  mandatory
--        DESCRIPTION
--        "A value which indicates the set of services that
--        this entity primarily offers.
--        The value is a sum.  This sum initially takes the
--        value zero, Then, for each layer, L, in the range
--        1 through 7, that this node performs transactions
--        for, 2 raised to (L - 1) is added to the sum.  For
--        example, a node which performs primarily routing
--        functions would have a value of 4 (2^(3-1)).  In
--        contrast, a node which is a host offering
--        application services would have a value of 72
--        (2^(4-1) + 2^(7-1)).  Note that in the context of
--        the Internet suite of protocols, values should be
--        calculated accordingly:
--        layer  functionality
--        1  physical (e.g., repeaters)
--        2  datalink/subnetwork (e.g., bridges)
--        3  internet (e.g., IP gateways)
--        4  end-to-end  (e.g., IP hosts)
--        7  applications (e.g., mail relays)
--        For systems including OSI protocols, layers 5 and
--        6 may also be counted."
--::= { system 7 }

--sysORLastChange OBJECT-TYPE
--        SYNTAX     TimeStamp
--        MAX-ACCESS read-only
--        STATUS     current
--        DESCRIPTION
--        "The value of sysUpTime at the time of the most recent
--        change in state or value of any instance of sysORID."
--::= { system 8 }

ifNumber  OBJECT-TYPE
        SYNTAX      Integer32
        MAX-ACCESS  read-only
        STATUS      current
        DESCRIPTION
        "The number of network interfaces (regardless of their
        current state) present on this system."
::= { interfaces 1 }

ifIndex OBJECT-TYPE
        SYNTAX      InterfaceIndex
        MAX-ACCESS  read-only
        STATUS      current
        DESCRIPTION
        "A unique value, greater than zero, for each interface.  It
        is recommended that values are assigned contiguously
        starting from 1.  The value for each interface sub-layer
        must remain constant at least from one re-initialization of
        the entity's network management system to the next re-
        initialization."
::= { ifEntry 1 }

ifDescr OBJECT-TYPE
        SYNTAX      DisplayString (SIZE (0..255))
        MAX-ACCESS  read-only
        STATUS      current
        DESCRIPTION
        "A textual string containing information about the
        interface.  This string should include the name of the
        manufacturer, the product name and the version of the
        interface hardware/software."
::= { ifEntry 2 }

ifType OBJECT-TYPE
        SYNTAX      IANAifType
        MAX-ACCESS  read-only
        STATUS      current
        DESCRIPTION
        "The type of interface.  Additional values for ifType are
        assigned by the Internet Assigned Numbers Authority (IANA),
        through updating the syntax of the IANAifType textual
        convention."
::= { ifEntry 3 }

ifMtu OBJECT-TYPE
        SYNTAX      Integer32
        MAX-ACCESS  read-only
        STATUS      current
        DESCRIPTION
        "The size of the largest packet which can be sent/received
        on the interface, specified in octets.  For interfaces that
        are used for transmitting network datagrams, this is the
        size of the largest network datagram that can be sent on the
        interface."
::= { ifEntry 4 }

ifSpeed OBJECT-TYPE
        SYNTAX      Gauge32
        MAX-ACCESS  read-only
        STATUS      current
        DESCRIPTION
        "An estimate of the interface's current bandwidth in bits
        per second.  For interfaces which do not vary in bandwidth
        or for those where no accurate estimation can be made, this
        object should contain the nominal bandwidth.  If the
        bandwidth of the interface is greater than the maximum value
        reportable by this object then this object should report its
        maximum value (4,294,967,295) and ifHighSpeed must be used
        to report the interace's speed.  For a sub-layer which has
        no concept of bandwidth, this object should be zero."
::= { ifEntry 5 }

ifPhysAddress OBJECT-TYPE
        SYNTAX      PhysAddress
        MAX-ACCESS  read-only
        STATUS      current
        DESCRIPTION
        "The interface's address at its protocol sub-layer.  For
        example, for an 802.x interface, this object normally
        contains a MAC address.  The interface's media-specific MIB
        must define the bit and byte ordering and the format of the
        value of this object.  For interfaces which do not have such
        an address (e.g., a serial line), this object should contain
        an octet string of zero length."
::= { ifEntry 6 }

ifAdminStatus OBJECT-TYPE
        SYNTAX  INTEGER {
        up(1),       -- ready to pass packets
        down(2),
        testing(3)   -- in some test mode
        }
        MAX-ACCESS  read-write
        STATUS      current
        DESCRIPTION
        "The desired state of the interface.  The testing(3) state
        indicates that no operational packets can be passed.  When a
        managed system initializes, all interfaces start with
        ifAdminStatus in the down(2) state.  As a result of either
        explicit management action or per configuration information
        retained by the managed system, ifAdminStatus is then
        changed to either the up(1) or testing(3) states (or remains
        in the down(2) state)."
::= { ifEntry 7 }

ifOperStatus OBJECT-TYPE
        SYNTAX  INTEGER {
        up(1),        -- ready to pass packets
        down(2),
        testing(3),   -- in some test mode
        unknown(4),   -- status can not be determined
        -- for some reason.
        dormant(5),
        notPresent(6),    -- some component is missing
        lowerLayerDown(7) -- down due to state of
        -- lower-layer interface(s)
        }
        MAX-ACCESS  read-only
        STATUS      current
        DESCRIPTION
        "The current operational state of the interface.  The
        testing(3) state indicates that no operational packets can
        be passed.  If ifAdminStatus is down(2) then ifOperStatus
        should be down(2).  If ifAdminStatus is changed to up(1)
        then ifOperStatus should change to up(1) if the interface is
        ready to transmit and receive network traffic; it should
        change to dormant(5) if the interface is waiting for
        external actions (such as a serial line waiting for an
        incoming connection); it should remain in the down(2) state
        if and only if there is a fault that prevents it from going
        to the up(1) state; it should remain in the notPresent(6)
        state if the interface has missing (typically, hardware)
        components."
::= { ifEntry 8 }

ifLastChange OBJECT-TYPE
        SYNTAX      TimeTicks
        MAX-ACCESS  read-only
        STATUS      current
        DESCRIPTION
        "The value of sysUpTime at the time the interface entered
        its current operational state.  If the current state was
        entered prior to the last re-initialization of the local
        network management subsystem, then this object contains a
        zero value."
::= { ifEntry 9 }

ifInOctets OBJECT-TYPE
        SYNTAX      Counter32
        MAX-ACCESS  read-only
        STATUS      current
        DESCRIPTION
        "The total number of octets received on the interface,
        including framing characters.
        Discontinuities in the value of this counter can occur at
        re-initialization of the management system, and at other
        times as indicated by the value of
        ifCounterDiscontinuityTime."
::= { ifEntry 10 }

ifInUcastPkts OBJECT-TYPE
        SYNTAX      Counter32
        MAX-ACCESS  read-only
        STATUS      current
        DESCRIPTION
        "The number of packets, delivered by this sub-layer to a
        higher (sub-)layer, which were not addressed to a multicast
        or broadcast address at this sub-layer.
        Discontinuities in the value of this counter can occur at
        re-initialization of the management system, and at other
        times as indicated by the value of
        ifCounterDiscontinuityTime."
::= { ifEntry 11 }

ifInNUcastPkts OBJECT-TYPE
        SYNTAX  Counter32
        MAX-ACCESS  read-only
        STATUS      deprecated
        DESCRIPTION
        "The number of packets, delivered by this sub-layer to a
        higher (sub-)layer, which were addressed to a multicast or
        broadcast address at this sub-layer.
        Discontinuities in the value of this counter can occur at
        re-initialization of the management system, and at other
        times as indicated by the value of
        ifCounterDiscontinuityTime.
        This object is deprecated in favour of ifInMulticastPkts and
        ifInBroadcastPkts."
::= { ifEntry 12 }

ifInDiscards OBJECT-TYPE
        SYNTAX      Counter32
        MAX-ACCESS  read-only
        STATUS      current
        DESCRIPTION
        "The number of inbound packets which were chosen to be
        discarded even though no errors had been detected to prevent
        their being deliverable to a higher-layer protocol.  One
        possible reason for discarding such a packet could be to
        free up buffer space.
        Discontinuities in the value of this counter can occur at
        re-initialization of the management system, and at other
        times as indicated by the value of
        ifCounterDiscontinuityTime."
::= { ifEntry 13 }

ifInErrors OBJECT-TYPE
        SYNTAX      Counter32
        MAX-ACCESS  read-only
        STATUS      current
        DESCRIPTION
        "For packet-oriented interfaces, the number of inbound
        packets that contained errors preventing them from being
        deliverable to a higher-layer protocol.  For character-
        oriented or fixed-length interfaces, the number of inbound
        transmission units that contained errors preventing them
        from being deliverable to a higher-layer protocol.
        Discontinuities in the value of this counter can occur at
        re-initialization of the management system, and at other
        times as indicated by the value of
        ifCounterDiscontinuityTime."
::= { ifEntry 14 }

ifInUnknownProtos OBJECT-TYPE
        SYNTAX      Counter32
        MAX-ACCESS  read-only
        STATUS      current
        DESCRIPTION
        "For packet-oriented interfaces, the number of packets
        received via the interface which were discarded because of
        an unknown or unsupported protocol.  For character-oriented
        or fixed-length interfaces that support protocol
        multiplexing the number of transmission units received via
        the interface which were discarded because of an unknown or
        unsupported protocol.  For any interface that does not
        support protocol multiplexing, this counter will always be
        0.
        Discontinuities in the value of this counter can occur at
        re-initialization of the management system, and at other
        times as indicated by the value of
        ifCounterDiscontinuityTime."
::= { ifEntry 15 }

ifOutOctets OBJECT-TYPE
        SYNTAX      Counter32
        MAX-ACCESS  read-only
        STATUS      current
        DESCRIPTION
        "The total number of octets transmitted out of the
        interface, including framing characters.
        Discontinuities in the value of this counter can occur at
        re-initialization of the management system, and at other
        times as indicated by the value of
        ifCounterDiscontinuityTime."
::= { ifEntry 16 }

ifOutUcastPkts OBJECT-TYPE
        SYNTAX      Counter32
        MAX-ACCESS  read-only
        STATUS      current
        DESCRIPTION
        "The total number of packets that higher-level protocols
        requested be transmitted, and which were not addressed to a
        multicast or broadcast address at this sub-layer, including
        those that were discarded or not sent.
        Discontinuities in the value of this counter can occur at
        re-initialization of the management system, and at other
        times as indicated by the value of
        ifCounterDiscontinuityTime."
::= { ifEntry 17 }

ifOutNUcastPkts OBJECT-TYPE
        SYNTAX      Counter32
        MAX-ACCESS  read-only
        STATUS      deprecated
        DESCRIPTION
        "The total number of packets that higher-level protocols
        requested be transmitted, and which were addressed to a
        multicast or broadcast address at this sub-layer, including
        those that were discarded or not sent.
        Discontinuities in the value of this counter can occur at
        re-initialization of the management system, and at other
        times as indicated by the value of
        ifCounterDiscontinuityTime.
        This object is deprecated in favour of ifOutMulticastPkts
        and ifOutBroadcastPkts."
::= { ifEntry 18 }

ifOutDiscards OBJECT-TYPE
        SYNTAX      Counter32
        MAX-ACCESS  read-only
        STATUS      current
        DESCRIPTION
        "The number of outbound packets which were chosen to be
        discarded even though no errors had been detected to prevent
        their being transmitted.  One possible reason for discarding
        such a packet could be to free up buffer space.
        Discontinuities in the value of this counter can occur at
        re-initialization of the management system, and at other
        times as indicated by the value of
        ifCounterDiscontinuityTime."
::= { ifEntry 19 }

ifOutErrors OBJECT-TYPE
        SYNTAX      Counter32
        MAX-ACCESS  read-only
        STATUS      current
        DESCRIPTION
        "For packet-oriented interfaces, the number of outbound
        packets that could not be transmitted because of errors.
        For character-oriented or fixed-length interfaces, the
        number of outbound transmission units that could not be
        transmitted because of errors.
        Discontinuities in the value of this counter can occur at
        re-initialization of the management system, and at other
        times as indicated by the value of
        ifCounterDiscontinuityTime."
::= { ifEntry 20 }

ifOutQLen OBJECT-TYPE
        SYNTAX      Gauge32
        MAX-ACCESS  read-only
        STATUS      deprecated
        DESCRIPTION
        "The length of the output packet queue (in packets)."
::= { ifEntry 21 }

ifSpecific OBJECT-TYPE
        SYNTAX      OBJECT IDENTIFIER
        MAX-ACCESS  read-only
        STATUS      deprecated
        DESCRIPTION
        "A reference to MIB definitions specific to the particular
        media being used to realize the interface.  It is
        recommended that this value point to an instance of a MIB
        object in the media-specific MIB, i.e., that this object
        have the semantics associated with the InstancePointer
        textual convention defined in RFC 2579.  In fact, it is
        recommended that the media-specific MIB specify what value
        ifSpecific should/can take for values of ifType.  If no MIB
        definitions specific to the particular media are available,
        the value should be set to the OBJECT IDENTIFIER { 0 0 }."
::= { ifEntry 22 }

atIfIndex OBJECT-TYPE
        SYNTAX  INTEGER
        ACCESS  read-write
        STATUS  deprecated
        DESCRIPTION
        "The interface on which this entry's equivalence
        is effective.  The interface identified by a
        particular value of this index is the same
        interface as identified by the same value of
        ifIndex."
::= { atEntry 1 }

atPhysAddress OBJECT-TYPE
        SYNTAX  PhysAddress
        ACCESS  read-write
        STATUS  deprecated
        DESCRIPTION
        "The media-dependent `physical' address.
        Setting this object to a null string (one of zero
        length) has the effect of invaliding the
        corresponding entry in the atTable object.  That
        is, it effectively dissasociates the interface
        identified with said entry from the mapping
        identified with said entry.  It is an
        implementation-specific matter as to whether the
        agent removes an invalidated entry from the table.
        Accordingly, management stations must be prepared
        to receive tabular information from agents that
        corresponds to entries not currently in use.
        Proper interpretation of such entries requires
        examination of the relevant atPhysAddress object."
::= { atEntry 2 }

atNetAddress OBJECT-TYPE
        SYNTAX  NetworkAddress
        ACCESS  read-write
        STATUS  deprecated
        DESCRIPTION
        "The NetworkAddress (e.g., the IP address)
        corresponding to the media-dependent `physical'
        address."
::= { atEntry 3 }

ipForwarding OBJECT-TYPE
        SYNTAX  INTEGER {
        forwarding(1),    -- acting as a gateway
        not-forwarding(2) -- NOT acting as a gateway
        }
        ACCESS  read-write
        STATUS  mandatory
        DESCRIPTION
        "The indication of whether this entity is acting
        as an IP gateway in respect to the forwarding of
        datagrams received by, but not addressed to, this
        entity.  IP gateways forward datagrams.  IP hosts
        do not (except those source-routed via the host).
        Note that for some managed nodes, this object may
        take on only a subset of the values possible.
        Accordingly, it is appropriate for an agent to
        return a `badValue' response if a management
        station attempts to change this object to an
        inappropriate value."
::= { ip 1 }

ipDefaultTTL OBJECT-TYPE
        SYNTAX  INTEGER
        ACCESS  read-write
        STATUS  mandatory
        DESCRIPTION
        "The default value inserted into the Time-To-Live
        field of the IP header of datagrams originated at
        this entity, whenever a TTL value is not supplied
        by the transport layer protocol."
::= { ip 2 }

ipInReceives OBJECT-TYPE
        SYNTAX  Counter
        ACCESS  read-only
        STATUS  mandatory
        DESCRIPTION
        "The total number of input datagrams received from
        interfaces, including those received in error."
::= { ip 3 }

ipInHdrErrors OBJECT-TYPE
        SYNTAX  Counter
        ACCESS  read-only
        STATUS  mandatory
        DESCRIPTION
        "The number of input datagrams discarded due to
        errors in their IP headers, including bad
        checksums, version number mismatch, other format
        errors, time-to-live exceeded, errors discovered
        in processing their IP options, etc."
::= { ip 4 }

ipInAddrErrors OBJECT-TYPE
        SYNTAX  Counter
        ACCESS  read-only
        STATUS  mandatory
        DESCRIPTION
        "The number of input datagrams discarded because
        the IP address in their IP header's destination
        field was not a valid address to be received at
        this entity.  This count includes invalid
        addresses (e.g., 0.0.0.0) and addresses of
        unsupported Classes (e.g., Class E).  For entities
        which are not IP Gateways and therefore do not
        forward datagrams, this counter includes datagrams
        discarded because the destination address was not
        a local address."
::= { ip 5 }

ipForwDatagrams OBJECT-TYPE
        SYNTAX  Counter
        ACCESS  read-only
        STATUS  mandatory
        DESCRIPTION
        "The number of input datagrams for which this
        entity was not their final IP destination, as a
        result of which an attempt was made to find a
        route to forward them to that final destination.
        In entities which do not act as IP Gateways, this
        counter will include only those packets which were
        Source-Routed via this entity, and the Source-
        Route option processing was successful."
::= { ip 6 }

ipInUnknownProtos OBJECT-TYPE
        SYNTAX  Counter
        ACCESS  read-only
        STATUS  mandatory
        DESCRIPTION
        "The number of locally-addressed datagrams
        received successfully but discarded because of an
        unknown or unsupported protocol."
::= { ip 7 }

ipInDiscards OBJECT-TYPE
        SYNTAX  Counter
        ACCESS  read-only
        STATUS  mandatory
        DESCRIPTION
        "The number of input IP datagrams for which no
        problems were encountered to prevent their
        continued processing, but which were discarded
        (e.g., for lack of buffer space).  Note that this
        counter does not include any datagrams discarded
        while awaiting re-assembly."
::= { ip 8 }

ipInDelivers OBJECT-TYPE
        SYNTAX  Counter
        ACCESS  read-only
        STATUS  mandatory
        DESCRIPTION
        "The total number of input datagrams successfully
        delivered to IP user-protocols (including ICMP)."
::= { ip 9 }

ipOutRequests OBJECT-TYPE
        SYNTAX  Counter
        ACCESS  read-only
        STATUS  mandatory
        DESCRIPTION
        "The total number of IP datagrams which local IP
        user-protocols (including ICMP) supplied to IP in
        requests for transmission.  Note that this counter
        does not include any datagrams counted in
        ipForwDatagrams."
::= { ip 10 }

ipOutDiscards OBJECT-TYPE
        SYNTAX  Counter
        ACCESS  read-only
        STATUS  mandatory
        DESCRIPTION
        "The number of output IP datagrams for which no
        problem was encountered to prevent their
        transmission to their destination, but which were
        discarded (e.g., for lack of buffer space).  Note
        that this counter would include datagrams counted
        in ipForwDatagrams if any such packets met this
        (discretionary) discard criterion."
::= { ip 11 }

ipOutNoRoutes OBJECT-TYPE
        SYNTAX  Counter
        ACCESS  read-only
        STATUS  mandatory
        DESCRIPTION
        "The number of IP datagrams discarded because no
        route could be found to transmit them to their
        destination.  Note that this counter includes any
        packets counted in ipForwDatagrams which meet this
        `no-route' criterion.  Note that this includes any
        datagarms which a host cannot route because all of
        its default gateways are down."
::= { ip 12 }

ipReasmTimeout OBJECT-TYPE
        SYNTAX  INTEGER
        ACCESS  read-only
        STATUS  mandatory
        DESCRIPTION
        "The maximum number of seconds which received
        fragments are held while they are awaiting
        reassembly at this entity."
::= { ip 13 }

ipReasmReqds OBJECT-TYPE
        SYNTAX  Counter
        ACCESS  read-only
        STATUS  mandatory
        DESCRIPTION
        "The number of IP fragments received which needed
        to be reassembled at this entity."
::= { ip 14 }

ipReasmOKs OBJECT-TYPE
        SYNTAX  Counter
        ACCESS  read-only
        STATUS  mandatory
        DESCRIPTION
        "The number of IP datagrams successfully re-
        assembled."
::= { ip 15 }

ipReasmFails OBJECT-TYPE
        SYNTAX  Counter
        ACCESS  read-only
        STATUS  mandatory
        DESCRIPTION
        "The number of failures detected by the IP re-
        assembly algorithm (for whatever reason: timed
        out, errors, etc).  Note that this is not
        necessarily a count of discarded IP fragments
        since some algorithms (notably the algorithm in
        RFC 815) can lose track of the number of fragments
        by combining them as they are received."
::= { ip 16 }

ipFragOKs OBJECT-TYPE
        SYNTAX  Counter
        ACCESS  read-only
        STATUS  mandatory
        DESCRIPTION
        "The number of IP datagrams that have been
        successfully fragmented at this entity."
::= { ip 17 }

ipFragFails OBJECT-TYPE
        SYNTAX  Counter
        ACCESS  read-only
        STATUS  mandatory
        DESCRIPTION
        "The number of IP datagrams that have been
        discarded because they needed to be fragmented at
        this entity but could not be, e.g., because their
        Don't Fragment flag was set."
::= { ip 18 }

ipFragCreates OBJECT-TYPE
        SYNTAX  Counter
        ACCESS  read-only
        STATUS  mandatory
        DESCRIPTION
        "The number of IP datagram fragments that have
        been generated as a result of fragmentation at
        this entity."
::= { ip 19 }

ipAdEntAddr OBJECT-TYPE
        SYNTAX  IpAddress
        ACCESS  read-only
        STATUS  mandatory
        DESCRIPTION
        "The IP address to which this entry's addressing
        information pertains."
::= { ipAddrEntry 1 }

ipAdEntIfIndex OBJECT-TYPE
        SYNTAX  INTEGER
        ACCESS  read-only
        STATUS  mandatory
        DESCRIPTION
        "The index value which uniquely identifies the
        interface to which this entry is applicable.  The
        interface identified by a particular value of this
        index is the same interface as identified by the
        same value of ifIndex."
::= { ipAddrEntry 2 }

ipAdEntNetMask OBJECT-TYPE
        SYNTAX  IpAddress
        ACCESS  read-only
        STATUS  mandatory
        DESCRIPTION
        "The subnet mask associated with the IP address of
        this entry.  The value of the mask is an IP
        address with all the network bits set to 1 and all
        the hosts bits set to 0."
::= { ipAddrEntry 3 }

ipAdEntBcastAddr OBJECT-TYPE
        SYNTAX  INTEGER
        ACCESS  read-only
        STATUS  mandatory
        DESCRIPTION
        "The value of the least-significant bit in the IP
        broadcast address used for sending datagrams on
        the (logical) interface associated with the IP
        address of this entry.  For example, when the
        Internet standard all-ones broadcast address is
        used, the value will be 1.  This value applies to
        both the subnet and network broadcasts addresses
        used by the entity on this (logical) interface."
::= { ipAddrEntry 4 }

ipAdEntReasmMaxSize OBJECT-TYPE
        SYNTAX  INTEGER (0..65535)
        ACCESS  read-only
        STATUS  mandatory
        DESCRIPTION
        "The size of the largest IP datagram which this
        entity can re-assemble from incoming IP fragmented
        datagrams received on this interface."
::= { ipAddrEntry 5 }

ipRouteDest OBJECT-TYPE
        SYNTAX  IpAddress
        ACCESS  read-write
        STATUS  mandatory
        DESCRIPTION
        "The destination IP address of this route.  An
        entry with a value of 0.0.0.0 is considered a
        default route.  Multiple routes to a single
        destination can appear in the table, but access to
        such multiple entries is dependent on the table-
        access mechanisms defined by the network
        management protocol in use."
::= { ipRouteEntry 1 }

ipRouteIfIndex OBJECT-TYPE
        SYNTAX  INTEGER
        ACCESS  read-write
        STATUS  mandatory
        DESCRIPTION
        "The index value which uniquely identifies the
        local interface through which the next hop of this
        route should be reached.  The interface identified
        by a particular value of this index is the same
        interface as identified by the same value of
        ifIndex."
::= { ipRouteEntry 2 }

ipRouteMetric1 OBJECT-TYPE
        SYNTAX  INTEGER
        ACCESS  read-write
        STATUS  mandatory
        DESCRIPTION
        "The primary routing metric for this route.  The
        semantics of this metric are determined by the
        routing-protocol specified in the route's
        ipRouteProto value.  If this metric is not used,
        its value should be set to -1."
::= { ipRouteEntry 3 }

ipRouteMetric2 OBJECT-TYPE
        SYNTAX  INTEGER
        ACCESS  read-write
        STATUS  mandatory
        DESCRIPTION
        "An alternate routing metric for this route.  The
        semantics of this metric are determined by the
        routing-protocol specified in the route's
        ipRouteProto value.  If this metric is not used,
        its value should be set to -1."
::= { ipRouteEntry 4 }

ipRouteMetric3 OBJECT-TYPE
        SYNTAX  INTEGER
        ACCESS  read-write
        STATUS  mandatory
        DESCRIPTION
        "An alternate routing metric for this route.  The
        semantics of this metric are determined by the
        routing-protocol specified in the route's
        ipRouteProto value.  If this metric is not used,
        its value should be set to -1."
::= { ipRouteEntry 5 }

ipRouteMetric4 OBJECT-TYPE
        SYNTAX  INTEGER
        ACCESS  read-write
        STATUS  mandatory
        DESCRIPTION
        "An alternate routing metric for this route.  The
        semantics of this metric are determined by the
        routing-protocol specified in the route's
        ipRouteProto value.  If this metric is not used,
        its value should be set to -1."
::= { ipRouteEntry 6 }

ipRouteNextHop OBJECT-TYPE
        SYNTAX  IpAddress
        ACCESS  read-write
        STATUS  mandatory
        DESCRIPTION
        "The IP address of the next hop of this route.
        (In the case of a route bound to an interface
        which is realized via a broadcast media, the value
        of this field is the agent's IP address on that
        interface.)"
::= { ipRouteEntry 7 }

ipRouteType OBJECT-TYPE
        SYNTAX  INTEGER {
        other(1),        -- none of the following
        invalid(2),      -- an invalidated route
        -- route to directly
        direct(3),       -- connected (sub-)network
        -- route to a non-local
        indirect(4)      -- host/network/sub-network
        }
        ACCESS  read-write
        STATUS  mandatory
        DESCRIPTION
        "The type of route.  Note that the values
        direct(3) and indirect(4) refer to the notion of
        direct and indirect routing in the IP
        architecture.
        Setting this object to the value invalid(2) has
        the effect of invalidating the corresponding entry
        in the ipRouteTable object.  That is, it
        effectively dissasociates the destination
        identified with said entry from the route
        identified with said entry.  It is an
        implementation-specific matter as to whether the
        agent removes an invalidated entry from the table.
        Accordingly, management stations must be prepared
        to receive tabular information from agents that
        corresponds to entries not currently in use.
        Proper interpretation of such entries requires
        examination of the relevant ipRouteType object."
::= { ipRouteEntry 8 }

ipRouteProto OBJECT-TYPE
        SYNTAX  INTEGER {
        other(1),       -- none of the following
        -- non-protocol information,
        -- e.g., manually configured
        local(2),       -- entries
        -- set via a network
        netmgmt(3),     -- management protocol
        -- obtained via ICMP,
        icmp(4),        -- e.g., Redirect
        -- the remaining values are
        -- all gateway routing
        -- protocols
        egp(5),
        ggp(6),
        hello(7),
        rip(8),
        is-is(9),
        es-is(10),
        ciscoIgrp(11),
        bbnSpfIgp(12),
        ospf(13),
        bgp(14)
        }
        ACCESS  read-only
        STATUS  mandatory
        DESCRIPTION
        "The routing mechanism via which this route was
        learned.  Inclusion of values for gateway routing
        protocols is not intended to imply that hosts
        should support those protocols."
::= { ipRouteEntry 9 }

ipRouteAge OBJECT-TYPE
        SYNTAX  INTEGER
        ACCESS  read-write
        STATUS  mandatory
        DESCRIPTION
        "The number of seconds since this route was last
        updated or otherwise determined to be correct.
        Note that no semantics of `too old' can be implied
        except through knowledge of the routing protocol
        by which the route was learned."
::= { ipRouteEntry 10 }

ipRouteMask OBJECT-TYPE
        SYNTAX  IpAddress
        ACCESS  read-write
        STATUS  mandatory
        DESCRIPTION
        "Indicate the mask to be logical-ANDed with the
        destination address before being compared to the
        value in the ipRouteDest field.  For those systems
        that do not support arbitrary subnet masks, an
        agent constructs the value of the ipRouteMask by
        determining whether the value of the correspondent
        ipRouteDest field belong to a class-A, B, or C
        network, and then using one of:
        mask           network
        255.0.0.0      class-A
        255.255.0.0    class-B
        255.255.255.0  class-C
        If the value of the ipRouteDest is 0.0.0.0 (a
        default route), then the mask value is also
        0.0.0.0.  It should be noted that all IP routing
        subsystems implicitly use this mechanism."
::= { ipRouteEntry 11 }

ipRouteMetric5 OBJECT-TYPE
        SYNTAX  INTEGER
        ACCESS  read-write
        STATUS  mandatory
        DESCRIPTION
        "An alternate routing metric for this route.  The
        semantics of this metric are determined by the
        routing-protocol specified in the route's
        ipRouteProto value.  If this metric is not used,
        its value should be set to -1."
::= { ipRouteEntry 12 }

ipRouteInfo OBJECT-TYPE
        SYNTAX  OBJECT IDENTIFIER
        ACCESS  read-only
        STATUS  mandatory
        DESCRIPTION
        "A reference to MIB definitions specific to the
        particular routing protocol which is responsible
        for this route, as determined by the value
        specified in the route's ipRouteProto value.  If
        this information is not present, its value should
        be set to the OBJECT IDENTIFIER { 0 0 }, which is
        a syntatically valid object identifier, and any
        conformant implementation of ASN.1 and BER must be
        able to generate and recognize this value."
::= { ipRouteEntry 13 }

ipNetToMediaIfIndex OBJECT-TYPE
        SYNTAX  INTEGER
        ACCESS  read-write
        STATUS  mandatory
        DESCRIPTION
        "The interface on which this entry's equivalence
        is effective.  The interface identified by a
        particular value of this index is the same
        interface as identified by the same value of
        ifIndex."
::= { ipNetToMediaEntry 1 }

ipNetToMediaPhysAddress OBJECT-TYPE
        SYNTAX  PhysAddress
        ACCESS  read-write
        STATUS  mandatory
        DESCRIPTION
        "The media-dependent `physical' address."
::= { ipNetToMediaEntry 2 }

ipNetToMediaNetAddress OBJECT-TYPE
        SYNTAX  IpAddress
        ACCESS  read-write
        STATUS  mandatory
        DESCRIPTION
        "The IpAddress corresponding to the media-
        dependent `physical' address."
::= { ipNetToMediaEntry 3 }

ipNetToMediaType OBJECT-TYPE
        SYNTAX  INTEGER {
        other(1),        -- none of the following
        invalid(2),      -- an invalidated mapping
        dynamic(3),
        static(4)
        }
        ACCESS  read-write
        STATUS  mandatory
        DESCRIPTION
        "The type of mapping.
        Setting this object to the value invalid(2) has
        the effect of invalidating the corresponding entry
        in the ipNetToMediaTable.  That is, it effectively
        dissasociates the interface identified with said
        entry from the mapping identified with said entry.
        It is an implementation-specific matter as to
        whether the agent removes an invalidated entry
        from the table.  Accordingly, management stations
        must be prepared to receive tabular information
        from agents that corresponds to entries not
        currently in use.  Proper interpretation of such
        entries requires examination of the relevant
        ipNetToMediaType object."
::= { ipNetToMediaEntry 4 }

ipRoutingDiscards OBJECT-TYPE
        SYNTAX  Counter
        ACCESS  read-only
        STATUS  mandatory
        DESCRIPTION
        "The number of routing entries which were chosen
        to be discarded even though they are valid.  One
        possible reason for discarding such an entry could
        be to free-up buffer space for other routing
        entries."
::= { ip 23 }

icmpInMsgs OBJECT-TYPE
        SYNTAX  Counter
        ACCESS  read-only
        STATUS  mandatory
        DESCRIPTION
        "The total number of ICMP messages which the
        entity received.  Note that this counter includes
        all those counted by icmpInErrors."
::= { icmp 1 }

icmpInErrors OBJECT-TYPE
        SYNTAX  Counter
        ACCESS  read-only
        STATUS  mandatory
        DESCRIPTION
        "The number of ICMP messages which the entity
        received but determined as having ICMP-specific
        errors (bad ICMP checksums, bad length, etc.)."
::= { icmp 2 }

icmpInDestUnreachs OBJECT-TYPE
        SYNTAX  Counter
        ACCESS  read-only
        STATUS  mandatory
        DESCRIPTION
        "The number of ICMP Destination Unreachable
        messages received."
::= { icmp 3 }

icmpInTimeExcds OBJECT-TYPE
        SYNTAX  Counter
        ACCESS  read-only
        STATUS  mandatory
        DESCRIPTION
        "The number of ICMP Time Exceeded messages
        received."
::= { icmp 4 }

icmpInParmProbs OBJECT-TYPE
        SYNTAX  Counter
        ACCESS  read-only
        STATUS  mandatory
        DESCRIPTION
        "The number of ICMP Parameter Problem messages
        received."
::= { icmp 5 }

icmpInSrcQuenchs OBJECT-TYPE
        SYNTAX  Counter
        ACCESS  read-only
        STATUS  mandatory
        DESCRIPTION
        "The number of ICMP Source Quench messages
        received."
::= { icmp 6 }

icmpInRedirects OBJECT-TYPE
        SYNTAX  Counter
        ACCESS  read-only
        STATUS  mandatory
        DESCRIPTION
        "The number of ICMP Redirect messages received."
::= { icmp 7 }

icmpInEchos OBJECT-TYPE
        SYNTAX  Counter
        ACCESS  read-only
        STATUS  mandatory
        DESCRIPTION
        "The number of ICMP Echo (request) messages
        received."
::= { icmp 8 }

icmpInEchoReps OBJECT-TYPE
        SYNTAX  Counter
        ACCESS  read-only
        STATUS  mandatory
        DESCRIPTION
        "The number of ICMP Echo Reply messages received."
::= { icmp 9 }

icmpInTimestamps OBJECT-TYPE
        SYNTAX  Counter
        ACCESS  read-only
        STATUS  mandatory
        DESCRIPTION
        "The number of ICMP Timestamp (request) messages
        received."
::= { icmp 10 }

icmpInTimestampReps OBJECT-TYPE
        SYNTAX  Counter
        ACCESS  read-only
        STATUS  mandatory
        DESCRIPTION
        "The number of ICMP Timestamp Reply messages
        received."
::= { icmp 11 }

icmpInAddrMasks OBJECT-TYPE
        SYNTAX  Counter
        ACCESS  read-only
        STATUS  mandatory
        DESCRIPTION
        "The number of ICMP Address Mask Request messages
        received."
::= { icmp 12 }

icmpInAddrMaskReps OBJECT-TYPE
        SYNTAX  Counter
        ACCESS  read-only
        STATUS  mandatory
        DESCRIPTION
        "The number of ICMP Address Mask Reply messages
        received."
::= { icmp 13 }

icmpOutMsgs OBJECT-TYPE
        SYNTAX  Counter
        ACCESS  read-only
        STATUS  mandatory
        DESCRIPTION
        "The total number of ICMP messages which this
        entity attempted to send.  Note that this counter
        includes all those counted by icmpOutErrors."
::= { icmp 14 }

icmpOutErrors OBJECT-TYPE
        SYNTAX  Counter
        ACCESS  read-only
        STATUS  mandatory
        DESCRIPTION
        "The number of ICMP messages which this entity did
        not send due to problems discovered within ICMP
        such as a lack of buffers.  This value should not
        include errors discovered outside the ICMP layer
        such as the inability of IP to route the resultant
        datagram.  In some implementations there may be no
        types of error which contribute to this counter's
        value."
::= { icmp 15 }

icmpOutDestUnreachs OBJECT-TYPE
        SYNTAX  Counter
        ACCESS  read-only
        STATUS  mandatory
        DESCRIPTION
        "The number of ICMP Destination Unreachable
        messages sent."
::= { icmp 16 }

icmpOutTimeExcds OBJECT-TYPE
        SYNTAX  Counter
        ACCESS  read-only
        STATUS  mandatory
        DESCRIPTION
        "The number of ICMP Time Exceeded messages sent."
::= { icmp 17 }

icmpOutParmProbs OBJECT-TYPE
        SYNTAX  Counter
        ACCESS  read-only
        STATUS  mandatory
        DESCRIPTION
        "The number of ICMP Parameter Problem messages
        sent."
::= { icmp 18 }

icmpOutSrcQuenchs OBJECT-TYPE
        SYNTAX  Counter
        ACCESS  read-only
        STATUS  mandatory
        DESCRIPTION
        "The number of ICMP Source Quench messages sent."
::= { icmp 19 }

icmpOutRedirects OBJECT-TYPE
        SYNTAX  Counter
        ACCESS  read-only
        STATUS  mandatory
        DESCRIPTION
        "The number of ICMP Redirect messages sent.  For a
        host, this object will always be zero, since hosts
        do not send redirects."
::= { icmp 20 }

icmpOutEchos OBJECT-TYPE
        SYNTAX  Counter
        ACCESS  read-only
        STATUS  mandatory
        DESCRIPTION
        "The number of ICMP Echo (request) messages sent."
::= { icmp 21 }

icmpOutEchoReps OBJECT-TYPE
        SYNTAX  Counter
        ACCESS  read-only
        STATUS  mandatory
        DESCRIPTION
        "The number of ICMP Echo Reply messages sent."
::= { icmp 22 }

icmpOutTimestamps OBJECT-TYPE
        SYNTAX  Counter
        ACCESS  read-only
        STATUS  mandatory
        DESCRIPTION
        "The number of ICMP Timestamp (request) messages
        sent."
::= { icmp 23 }

icmpOutTimestampReps OBJECT-TYPE
        SYNTAX  Counter
        ACCESS  read-only
        STATUS  mandatory
        DESCRIPTION
        "The number of ICMP Timestamp Reply messages
        sent."
::= { icmp 24 }

icmpOutAddrMasks OBJECT-TYPE
        SYNTAX  Counter
        ACCESS  read-only
        STATUS  mandatory
        DESCRIPTION
        "The number of ICMP Address Mask Request messages
        sent."
::= { icmp 25 }

icmpOutAddrMaskReps OBJECT-TYPE
        SYNTAX  Counter
        ACCESS  read-only
        STATUS  mandatory
        DESCRIPTION
        "The number of ICMP Address Mask Reply messages
        sent."
::= { icmp 26 }

tcpRtoAlgorithm OBJECT-TYPE
        SYNTAX  INTEGER {
        other(1),    -- none of the following
        constant(2), -- a constant rto
        rsre(3),     -- MIL-STD-1778, Appendix B
        vanj(4)      -- Van Jacobson's algorithm [10]
        }
        ACCESS  read-only
        STATUS  mandatory
        DESCRIPTION
        "The algorithm used to determine the timeout value
        used for retransmitting unacknowledged octets."
::= { tcp 1 }

tcpRtoMin OBJECT-TYPE
        SYNTAX  INTEGER
        ACCESS  read-only
        STATUS  mandatory
        DESCRIPTION
        "The minimum value permitted by a TCP
        implementation for the retransmission timeout,
        measured in milliseconds.  More refined semantics
        for objects of this type depend upon the algorithm
        used to determine the retransmission timeout.  In
        particular, when the timeout algorithm is rsre(3),
        an object of this type has the semantics of the
        LBOUND quantity described in RFC 793."
::= { tcp 2 }

tcpRtoMax OBJECT-TYPE
        SYNTAX  INTEGER
        ACCESS  read-only
        STATUS  mandatory
        DESCRIPTION
        "The maximum value permitted by a TCP
        implementation for the retransmission timeout,
        measured in milliseconds.  More refined semantics
        for objects of this type depend upon the algorithm
        used to determine the retransmission timeout.  In
        particular, when the timeout algorithm is rsre(3),
        an object of this type has the semantics of the
        UBOUND quantity described in RFC 793."
::= { tcp 3 }

tcpMaxConn OBJECT-TYPE
        SYNTAX  INTEGER
        ACCESS  read-only
        STATUS  mandatory
        DESCRIPTION
        "The limit on the total number of TCP connections
        the entity can support.  In entities where the
        maximum number of connections is dynamic, this
        object should contain the value -1."
::= { tcp 4 }

tcpActiveOpens OBJECT-TYPE
        SYNTAX  Counter
        ACCESS  read-only
        STATUS  mandatory
        DESCRIPTION
        "The number of times TCP connections have made a
        direct transition to the SYN-SENT state from the
        CLOSED state."
::= { tcp 5 }

tcpPassiveOpens OBJECT-TYPE
        SYNTAX  Counter
        ACCESS  read-only
        STATUS  mandatory
        DESCRIPTION
        "The number of times TCP connections have made a
        direct transition to the SYN-RCVD state from the
        LISTEN state."
::= { tcp 6 }

tcpAttemptFails OBJECT-TYPE
        SYNTAX  Counter
        ACCESS  read-only
        STATUS  mandatory
        DESCRIPTION
        "The number of times TCP connections have made a
        direct transition to the CLOSED state from either
        the SYN-SENT state or the SYN-RCVD state, plus the
        number of times TCP connections have made a direct
        transition to the LISTEN state from the SYN-RCVD
        state."
::= { tcp 7 }

tcpEstabResets OBJECT-TYPE
        SYNTAX  Counter
        ACCESS  read-only
        STATUS  mandatory
        DESCRIPTION
        "The number of times TCP connections have made a
        direct transition to the CLOSED state from either
        the ESTABLISHED state or the CLOSE-WAIT state."
::= { tcp 8 }

tcpCurrEstab OBJECT-TYPE
        SYNTAX  Gauge
        ACCESS  read-only
        STATUS  mandatory
        DESCRIPTION
        "The number of TCP connections for which the
        current state is either ESTABLISHED or CLOSE-
        WAIT."
::= { tcp 9 }

tcpInSegs OBJECT-TYPE
        SYNTAX  Counter
        ACCESS  read-only
        STATUS  mandatory
        DESCRIPTION
        "The total number of segments received, including
        those received in error.  This count includes
        segments received on currently established
        connections."
::= { tcp 10 }

tcpOutSegs OBJECT-TYPE
        SYNTAX  Counter
        ACCESS  read-only
        STATUS  mandatory
        DESCRIPTION
        "The total number of segments sent, including
        those on current connections but excluding those
        containing only retransmitted octets."
::= { tcp 11 }

tcpRetransSegs OBJECT-TYPE
        SYNTAX  Counter
        ACCESS  read-only
        STATUS  mandatory
        DESCRIPTION
        "The total number of segments retransmitted - that
        is, the number of TCP segments transmitted
        containing one or more previously transmitted
        octets."
::= { tcp 12 }

tcpConnState OBJECT-TYPE
        SYNTAX  INTEGER {
        closed(1),
        listen(2),
        synSent(3),
        synReceived(4),
        established(5),
        finWait1(6),
        finWait2(7),
        closeWait(8),
        lastAck(9),
        closing(10),
        timeWait(11),
        deleteTCB(12)
        }
        ACCESS  read-write
        STATUS  mandatory
        DESCRIPTION
        "The state of this TCP connection.
        The only value which may be set by a management
        station is deleteTCB(12).  Accordingly, it is
        appropriate for an agent to return a `badValue'
        response if a management station attempts to set
        this object to any other value.
        If a management station sets this object to the
        value deleteTCB(12), then this has the effect of
        deleting the TCB (as defined in RFC 793) of the
        corresponding connection on the managed node,
        resulting in immediate termination of the
        connection.
        As an implementation-specific option, a RST
        segment may be sent from the managed node to the
        other TCP endpoint (note however that RST segments
        are not sent reliably)."
::= { tcpConnEntry 1 }

tcpConnLocalAddress OBJECT-TYPE
        SYNTAX  IpAddress
        ACCESS  read-only
        STATUS  mandatory
        DESCRIPTION
        "The local IP address for this TCP connection.  In
        the case of a connection in the listen state which
        is willing to accept connections for any IP
        interface associated with the node, the value
        0.0.0.0 is used."
::= { tcpConnEntry 2 }

tcpConnLocalPort OBJECT-TYPE
        SYNTAX  INTEGER (0..65535)
        ACCESS  read-only
        STATUS  mandatory
        DESCRIPTION
        "The local port number for this TCP connection."
::= { tcpConnEntry 3 }

tcpConnRemAddress OBJECT-TYPE
        SYNTAX  IpAddress
        ACCESS  read-only
        STATUS  mandatory
        DESCRIPTION
        "The remote IP address for this TCP connection."
::= { tcpConnEntry 4 }

tcpConnRemPort OBJECT-TYPE
        SYNTAX  INTEGER (0..65535)
        ACCESS  read-only
        STATUS  mandatory
        DESCRIPTION
        "The remote port number for this TCP connection."
::= { tcpConnEntry 5 }

tcpInErrs OBJECT-TYPE
        SYNTAX  Counter
        ACCESS  read-only
        STATUS  mandatory
        DESCRIPTION
        "The total number of segments received in error
        (e.g., bad TCP checksums)."
::= { tcp 14 }

tcpOutRsts OBJECT-TYPE
        SYNTAX  Counter
        ACCESS  read-only
        STATUS  mandatory
        DESCRIPTION
        "The number of TCP segments sent containing the
        RST flag."
::= { tcp 15 }

udpInDatagrams OBJECT-TYPE
        SYNTAX     Counter32
        MAX-ACCESS read-only
        STATUS     current
        DESCRIPTION
        "The total number of UDP datagrams delivered to UDP
        users.
        Discontinuities in the value of this counter can occur
        at re-initialization of the management system, and at
        other times as indicated by discontinuities in the
        value of sysUpTime."
::= { udp 1 }

udpNoPorts OBJECT-TYPE
        SYNTAX     Counter32
        MAX-ACCESS read-only
        STATUS     current
        DESCRIPTION
        "The total number of received UDP datagrams for which
        there was no application at the destination port.
        Discontinuities in the value of this counter can occur
        at re-initialization of the management system, and at
        other times as indicated by discontinuities in the
        value of sysUpTime."
::= { udp 2 }

udpInErrors OBJECT-TYPE
        SYNTAX     Counter32
        MAX-ACCESS read-only
        STATUS     current
        DESCRIPTION
        "The number of received UDP datagrams that could not be
        delivered for reasons other than the lack of an
        application at the destination port.
        Discontinuities in the value of this counter can occur
        at re-initialization of the management system, and at
        other times as indicated by discontinuities in the
        value of sysUpTime."
::= { udp 3 }

udpOutDatagrams OBJECT-TYPE
        SYNTAX     Counter32
        MAX-ACCESS read-only
        STATUS     current
        DESCRIPTION
        "The total number of UDP datagrams sent from this
        entity.
        Discontinuities in the value of this counter can occur
        at re-initialization of the management system, and at
        other times as indicated by discontinuities in the
        value of sysUpTime."
::= { udp 4 }

udpLocalAddress OBJECT-TYPE
        SYNTAX     IpAddress
        MAX-ACCESS read-only
        STATUS     deprecated
        DESCRIPTION
        "The local IP address for this UDP listener.  In the
        case of a UDP listener that is willing to accept
        datagrams for any IP interface associated with the
        node, the value 0.0.0.0 is used."
::= { udpEntry 1 }

udpLocalPort OBJECT-TYPE
        SYNTAX     Integer32 (0..65535)
        MAX-ACCESS read-only
        STATUS     deprecated
        DESCRIPTION
        "The local port number for this UDP listener."
::= { udpEntry 2 }

snmpInPkts OBJECT-TYPE
        SYNTAX  Counter
        ACCESS  read-only
        STATUS  mandatory
        DESCRIPTION
        "The total number of Messages delivered to the
        SNMP entity from the transport service."
::= { snmp 1 }

snmpOutPkts OBJECT-TYPE
        SYNTAX  Counter
        ACCESS  read-only
        STATUS  mandatory
        DESCRIPTION
        "The total number of SNMP Messages which were
        passed from the SNMP protocol entity to the
        transport service."
::= { snmp 2 }

snmpInBadVersions OBJECT-TYPE
        SYNTAX  Counter
        ACCESS  read-only
        STATUS  mandatory
        DESCRIPTION
        "The total number of SNMP Messages which were
        delivered to the SNMP protocol entity and were for
        an unsupported SNMP version."
::= { snmp 3 }

snmpInBadCommunityNames OBJECT-TYPE
        SYNTAX  Counter
        ACCESS  read-only
        STATUS  mandatory
        DESCRIPTION
        "The total number of SNMP Messages delivered to
        the SNMP protocol entity which used a SNMP
        community name not known to said entity."
::= { snmp 4 }

snmpInBadCommunityUses OBJECT-TYPE
        SYNTAX  Counter
        ACCESS  read-only
        STATUS  mandatory
        DESCRIPTION
        "The total number of SNMP Messages delivered to
        the SNMP protocol entity which represented an SNMP
        operation which was not allowed by the SNMP
        community named in the Message."
::= { snmp 5 }

snmpInASNParseErrs OBJECT-TYPE
        SYNTAX  Counter
        ACCESS  read-only
        STATUS  mandatory
        DESCRIPTION
        "The total number of ASN.1 or BER errors
        encountered by the SNMP protocol entity when
        decoding received SNMP Messages."
::= { snmp 6 }

snmpInTooBigs OBJECT-TYPE
        SYNTAX  Counter
        ACCESS  read-only
        STATUS  mandatory
        DESCRIPTION
        "The total number of SNMP PDUs which were
        delivered to the SNMP protocol entity and for
        which the value of the error-status field is
        `tooBig'."
::= { snmp 8 }

snmpInNoSuchNames OBJECT-TYPE
        SYNTAX  Counter
        ACCESS  read-only
        STATUS  mandatory
        DESCRIPTION
        "The total number of SNMP PDUs which were
        delivered to the SNMP protocol entity and for
        which the value of the error-status field is
        `noSuchName'."
::= { snmp 9 }

snmpInBadValues OBJECT-TYPE
        SYNTAX  Counter
        ACCESS  read-only
        STATUS  mandatory
        DESCRIPTION
        "The total number of SNMP PDUs which were
        delivered to the SNMP protocol entity and for
        which the value of the error-status field is
        `badValue'."
::= { snmp 10 }

snmpInReadOnlys OBJECT-TYPE
        SYNTAX  Counter
        ACCESS  read-only
        STATUS  mandatory
        DESCRIPTION
        "The total number valid SNMP PDUs which were
        delivered to the SNMP protocol entity and for
        which the value of the error-status field is
        `readOnly'.  It should be noted that it is a
        protocol error to generate an SNMP PDU which
        contains the value `readOnly' in the error-status
        field, as such this object is provided as a means
        of detecting incorrect implementations of the
        SNMP."
::= { snmp 11 }

snmpInGenErrs OBJECT-TYPE
        SYNTAX  Counter
        ACCESS  read-only
        STATUS  mandatory
        DESCRIPTION
        "The total number of SNMP PDUs which were
        delivered to the SNMP protocol entity and for
        which the value of the error-status field is
        `genErr'."
::= { snmp 12 }

snmpInTotalReqVars OBJECT-TYPE
        SYNTAX  Counter
        ACCESS  read-only
        STATUS  mandatory
        DESCRIPTION
        "The total number of MIB objects which have been
        retrieved successfully by the SNMP protocol entity
        as the result of receiving valid SNMP Get-Request
        and Get-Next PDUs."
::= { snmp 13 }

snmpInTotalSetVars OBJECT-TYPE
        SYNTAX  Counter
        ACCESS  read-only
        STATUS  mandatory
        DESCRIPTION
        "The total number of MIB objects which have been
        altered successfully by the SNMP protocol entity
        as the result of receiving valid SNMP Set-Request
        PDUs."
::= { snmp 14 }

snmpInGetRequests OBJECT-TYPE
        SYNTAX  Counter
        ACCESS  read-only
        STATUS  mandatory
        DESCRIPTION
        "The total number of SNMP Get-Request PDUs which
        have been accepted and processed by the SNMP
        protocol entity."
::= { snmp 15 }

snmpInGetNexts OBJECT-TYPE
        SYNTAX  Counter
        ACCESS  read-only
        STATUS  mandatory
        DESCRIPTION
        "The total number of SNMP Get-Next PDUs which have
        been accepted and processed by the SNMP protocol
        entity."
::= { snmp 16 }

snmpInSetRequests OBJECT-TYPE
        SYNTAX  Counter
        ACCESS  read-only
        STATUS  mandatory
        DESCRIPTION
        "The total number of SNMP Set-Request PDUs which
        have been accepted and processed by the SNMP
        protocol entity."
::= { snmp 17 }

snmpInGetResponses OBJECT-TYPE
        SYNTAX  Counter
        ACCESS  read-only
        STATUS  mandatory
        DESCRIPTION
        "The total number of SNMP Get-Response PDUs which
        have been accepted and processed by the SNMP
        protocol entity."
::= { snmp 18 }

snmpInTraps OBJECT-TYPE
        SYNTAX  Counter
        ACCESS  read-only
        STATUS  mandatory
        DESCRIPTION
        "The total number of SNMP Trap PDUs which have
        been accepted and processed by the SNMP protocol
        entity."
::= { snmp 19 }

snmpOutTooBigs OBJECT-TYPE
        SYNTAX  Counter
        ACCESS  read-only
        STATUS  mandatory
        DESCRIPTION
        "The total number of SNMP PDUs which were
        generated by the SNMP protocol entity and for
        which the value of the error-status field is
        `tooBig.'"
::= { snmp 20 }

snmpOutNoSuchNames OBJECT-TYPE
        SYNTAX  Counter
        ACCESS  read-only
        STATUS  mandatory
        DESCRIPTION
        "The total number of SNMP PDUs which were
        generated by the SNMP protocol entity and for
        which the value of the error-status is
        `noSuchName'."
::= { snmp 21 }

snmpOutBadValues OBJECT-TYPE
        SYNTAX  Counter
        ACCESS  read-only
        STATUS  mandatory
        DESCRIPTION
        "The total number of SNMP PDUs which were
        generated by the SNMP protocol entity and for
        which the value of the error-status field is
        `badValue'."
::= { snmp 22 }

snmpOutGenErrs OBJECT-TYPE
        SYNTAX  Counter
        ACCESS  read-only
        STATUS  mandatory
        DESCRIPTION
        "The total number of SNMP PDUs which were
        generated by the SNMP protocol entity and for
        which the value of the error-status field is
        `genErr'."
::= { snmp 24 }

snmpOutGetRequests OBJECT-TYPE
        SYNTAX  Counter
        ACCESS  read-only
        STATUS  mandatory
        DESCRIPTION
        "The total number of SNMP Get-Request PDUs which
        have been generated by the SNMP protocol entity."
::= { snmp 25 }

snmpOutGetNexts OBJECT-TYPE
        SYNTAX  Counter
        ACCESS  read-only
        STATUS  mandatory
        DESCRIPTION
        "The total number of SNMP Get-Next PDUs which have
        been generated by the SNMP protocol entity."
::= { snmp 26 }

snmpOutSetRequests OBJECT-TYPE
        SYNTAX  Counter
        ACCESS  read-only
        STATUS  mandatory
        DESCRIPTION
        "The total number of SNMP Set-Request PDUs which
        have been generated by the SNMP protocol entity."
::= { snmp 27 }

snmpOutGetResponses OBJECT-TYPE
        SYNTAX  Counter
        ACCESS  read-only
        STATUS  mandatory
        DESCRIPTION
        "The total number of SNMP Get-Response PDUs which
        have been generated by the SNMP protocol entity."
::= { snmp 28 }

snmpOutTraps OBJECT-TYPE
        SYNTAX  Counter
        ACCESS  read-only
        STATUS  mandatory
        DESCRIPTION
        "The total number of SNMP Trap PDUs which have
        been generated by the SNMP protocol entity."
::= { snmp 29 }

snmpEnableAuthenTraps OBJECT-TYPE
        SYNTAX  INTEGER { enabled(1), disabled(2) }
        ACCESS  read-write
        STATUS  mandatory
        DESCRIPTION
        "Indicates whether the SNMP agent process is
        permitted to generate authentication-failure
        traps.  The value of this object overrides any
        configuration information; as such, it provides a
        means whereby all authentication-failure traps may
        be disabled.
        Note that it is strongly recommended that this
        object be stored in non-volatile memory so that it
        remains constant between re-initializations of the
        network management system."
::= { snmp 30 }

hrSystemUptime OBJECT-TYPE
        SYNTAX     TimeTicks
        MAX-ACCESS read-only
        STATUS     current
        DESCRIPTION
        "The amount of time since this host was last
        initialized.  Note that this is different from
        sysUpTime in the SNMPv2-MIB [RFC1907] because
        sysUpTime is the uptime of the network management
        portion of the system."
::= { hrSystem 1 }

hrMemorySize OBJECT-TYPE
        SYNTAX     KBytes
        UNITS      "KBytes"
        MAX-ACCESS read-only
        STATUS     current
        DESCRIPTION
        "The amount of physical read-write main memory,
        typically RAM, contained by the host."
::= { hrStorage 2 }

hrStorageIndex OBJECT-TYPE
        SYNTAX     Integer32 (1..2147483647)
        MAX-ACCESS read-only
        STATUS     current
        DESCRIPTION
        "A unique value for each logical storage area
        contained by the host."
::= { hrStorageEntry 1 }

hrStorageType OBJECT-TYPE
        SYNTAX     AutonomousType
        MAX-ACCESS read-only
        STATUS     current
        DESCRIPTION
        "The type of storage represented by this entry."
::= { hrStorageEntry 2 }

hrStorageDescr OBJECT-TYPE
        SYNTAX     DisplayString
        MAX-ACCESS read-only
        STATUS     current
        DESCRIPTION
        "A description of the type and instance of the storage
        described by this entry."
::= { hrStorageEntry 3 }

hrStorageAllocationUnits OBJECT-TYPE
        SYNTAX     Integer32 (1..2147483647)
        UNITS      "Bytes"
        MAX-ACCESS read-only
        STATUS     current
        DESCRIPTION
        "The size, in bytes, of the data objects allocated
        from this pool.  If this entry is monitoring sectors,
        blocks, buffers, or packets, for example, this number
        will commonly be greater than one.  Otherwise this
        number will typically be one."
::= { hrStorageEntry 4 }

hrStorageSize OBJECT-TYPE
        SYNTAX     Integer32 (0..2147483647)
        MAX-ACCESS read-write
        STATUS     current
        DESCRIPTION
        "The size of the storage represented by this entry, in
        units of hrStorageAllocationUnits. This object is
        writable to allow remote configuration of the size of
        the storage area in those cases where such an
        operation makes sense and is possible on the
        underlying system. For example, the amount of main
        memory allocated to a buffer pool might be modified or
        the amount of disk space allocated to virtual memory
        might be modified."
::= { hrStorageEntry 5 }

hrStorageUsed OBJECT-TYPE
        SYNTAX     Integer32 (0..2147483647)
        MAX-ACCESS read-only
        STATUS     current
        DESCRIPTION
        "The amount of the storage represented by this entry
        that is allocated, in units of
        hrStorageAllocationUnits."
::= { hrStorageEntry 6 }

hrStorageAllocationFailures OBJECT-TYPE
        SYNTAX     Counter32
        MAX-ACCESS read-only
        STATUS     current
        DESCRIPTION
        "The number of requests for storage represented by
        this entry that could not be honored due to not enough
        storage.  It should be noted that as this object has a
        SYNTAX of Counter32, that it does not have a defined
        initial value.  However, it is recommended that this
        object be initialized to zero, even though management
        stations must not depend on such an initialization."
::= { hrStorageEntry 7 }

hrDeviceIndex OBJECT-TYPE
        SYNTAX     Integer32 (1..2147483647)
        MAX-ACCESS read-only
        STATUS     current
        DESCRIPTION
        "A unique value for each device contained by the host.
        The value for each device must remain constant at
        least from one re-initialization of the agent to the
        next re-initialization."
::= { hrDeviceEntry 1 }

hrDeviceType OBJECT-TYPE
        SYNTAX     AutonomousType
        MAX-ACCESS read-only
        STATUS     current
        DESCRIPTION
        "An indication of the type of device.
        If this value is
        `hrDeviceProcessor { hrDeviceTypes 3 }' then an entry
        exists in the hrProcessorTable which corresponds to
        this device.
        If this value is
        `hrDeviceNetwork { hrDeviceTypes 4 }', then an entry
        exists in the hrNetworkTable which corresponds to this
        device.
        If this value is
        `hrDevicePrinter { hrDeviceTypes 5 }', then an entry
        exists in the hrPrinterTable which corresponds to this
        device.
        If this value is
        `hrDeviceDiskStorage { hrDeviceTypes 6 }', then an
        entry exists in the hrDiskStorageTable which
        corresponds to this device."
::= { hrDeviceEntry 2 }

hrDeviceDescr OBJECT-TYPE
        SYNTAX     DisplayString (SIZE (0..64))
        MAX-ACCESS read-only
        STATUS     current
        DESCRIPTION
        "A textual description of this device, including the
        device's manufacturer and revision, and optionally,
        its serial number."
::= { hrDeviceEntry 3 }

hrDeviceID OBJECT-TYPE
        SYNTAX     ProductID
        MAX-ACCESS read-only
        STATUS     current
        DESCRIPTION
        "The product ID for this device."
::= { hrDeviceEntry 4 }

hrDeviceStatus OBJECT-TYPE
        SYNTAX     INTEGER {
        unknown(1),
        running(2),
        warning(3),
        testing(4),
        down(5)
        }
        MAX-ACCESS read-only
        STATUS     current
        DESCRIPTION
        "The current operational state of the device described
        by this row of the table.  A value unknown(1)
        indicates that the current state of the device is
        unknown.  running(2) indicates that the device is up
        and running and that no unusual error conditions are
        known.  The warning(3) state indicates that agent has
        been informed of an unusual error condition by the
        operational software (e.g., a disk device driver) but
        that the device is still 'operational'.  An example
        would be a high number of soft errors on a disk.  A
        value of testing(4), indicates that the device is not
        available for use because it is in the testing state.
        The state of down(5) is used only when the agent has
        been informed that the device is not available for any
        use."
::= { hrDeviceEntry 5 }

hrDeviceErrors OBJECT-TYPE
        SYNTAX     Counter32
        MAX-ACCESS read-only
        STATUS     current
        DESCRIPTION
        "The number of errors detected on this device.  It
        should be noted that as this object has a SYNTAX of
        Counter32, that it does not have a defined initial
        value.  However, it is recommended that this object be
        initialized to zero, even though management stations
        must not depend on such an initialization."
::= { hrDeviceEntry 6 }

hrPrinterStatus OBJECT-TYPE
        SYNTAX     INTEGER {
        other(1),
        unknown(2),
        idle(3),
        printing(4),
        warmup(5)
        }
        MAX-ACCESS read-only
        STATUS     current
        DESCRIPTION
        "The current status of this printer device."
::= { hrPrinterEntry 1 }

hrPrinterDetectedErrorState OBJECT-TYPE
        SYNTAX     OCTET STRING
        MAX-ACCESS read-only
        STATUS     current
        DESCRIPTION
        "This object represents any error conditions detected
        by the printer.  The error conditions are encoded as
        bits in an octet string, with the following
        definitions:
        Condition         Bit #
        lowPaper              0
        noPaper               1
        lowToner              2
        noToner               3
        doorOpen              4
        jammed                5
        offline               6
        serviceRequested      7
        inputTrayMissing      8
        outputTrayMissing     9
        markerSupplyMissing  10
        outputNearFull       11
        outputFull           12
        inputTrayEmpty       13
        overduePreventMaint  14
        Bits are numbered starting with the most significant
        bit of the first byte being bit 0, the least
        significant bit of the first byte being bit 7, the
        most significant bit of the second byte being bit 8,
        and so on.  A one bit encodes that the condition was
        detected, while a zero bit encodes that the condition
        was not detected.
        This object is useful for alerting an operator to
        specific warning or error conditions that may occur,
        especially those requiring human intervention."
::= { hrPrinterEntry 2 }

prtGeneralConfigChanges OBJECT-TYPE
        SYNTAX     Counter32
        MAX-ACCESS read-only
        STATUS     current
        DESCRIPTION
        "Counts configuration changes within the printer. A
        configuration change is defined to be an action that results in
        a change to any MIB object other than those that reflect status
        or level, or those that act as counters or gauges. In addition,
        any action that results in a row being added or deleted from
        any table in the Printer MIB is considered a configuration
        change. Such changes will often affect the capability of the
        printer to service certain types of print jobs. Management
        applications may cache infrequently changed configuration
        information about sub units within the printer. This object
        should be incremented whenever the agent wishes to notify
        management applications that any cached configuration
        information for this device is to be considered 'stale'. At
        this point, the management application should flush any
        configuration information cached about this device and fetch
        new configuration information.
        The following are examples of actions that would cause the
        prtGeneralConfigChanges object to be incremented:
        - Adding an output bin
        - Changing the media in a sensing input tray
        - Changing the value of prtInputMediaType
        Note that the prtGeneralConfigChanges counter would not be
        incremented when an input tray is temporarily removed to load
        additional paper or when the level of an input device changes.
        NOTE: The above description has been modified from RFC 1759
        for clarification."
::= { prtGeneralEntry 1 }

prtGeneralCurrentLocalization OBJECT-TYPE
        SYNTAX     Integer32 (1..65535)
        MAX-ACCESS read-write
        STATUS     current
        DESCRIPTION
        "The value of the prtLocalizationIndex corresponding to the
        current language, country, and character set to be used for
        localized string values that are identified as being dependent
        on the value of this object.  Note that this object does not
        apply to localized strings in the prtConsole group or to any
        object that is not explicitly identified as being localized
        according to prtGeneralCurrentLocalization.  When an object's
        'charset' is controlled by the value of
        prtGeneralCurrentLocalization, it MUST specify
        PrtLocalizedDescriptionStringTC as its syntax.
        NOTE: The above description has been modified from RFC 1759
        for clarification."
::= { prtGeneralEntry 2 }

prtGeneralReset OBJECT-TYPE
        -- NOTE: In RFC 1759, the enumeration values were implicitly defined
        -- by this object.
        SYNTAX     PrtGeneralResetTC
        MAX-ACCESS read-write
        STATUS     current
        DESCRIPTION
        "Setting this value to 'powerCycleReset', 'resetToNVRAM', or
        'resetToFactoryDefaults' will result in the resetting of the
        printer.  When read, this object will always have the value
        'notResetting(3)', and a SET of the value 'notResetting' shall
        have no effect on the printer.  Some of the defined values are
        optional.  However, every implementation must support at least
        the values 'notResetting' and 'resetToNVRAM'."
::= { prtGeneralEntry 3 }

prtGeneralCurrentOperator OBJECT-TYPE
        SYNTAX     OCTET STRING (SIZE(0..127))
        MAX-ACCESS read-write
        STATUS     current
        DESCRIPTION
        "The name of the person who is responsible for operating
        this printer.  It is suggested that this string include
        information that would enable other humans to reach the
        operator, such as a phone number.  As a convention to
        facilitate automatic notification of the operator by the
        agent or network management station, the phone number,
        fax number or email address should be indicated by the
        URL schemes 'tel:', 'fax:' and 'mailto:', respectively.
        If either the phone, fax, or email information is not
        available, then a line should not be included for this
        information.
        NOTE: For interoperability purposes, it is advisable to
        use email addresses formatted according to [RFC2822]
        requirements.
        NOTE: The above description has been modified from RFC 1759
        for clarification."
::= { prtGeneralEntry 4 }

prtGeneralServicePerson OBJECT-TYPE
        SYNTAX     OCTET STRING (SIZE(0..127))
        MAX-ACCESS read-write
        STATUS     current
        DESCRIPTION
        "The name of the person responsible for servicing this
        printer.  It is suggested that this string include
        information that would enable other humans to reach the
        service person, such as a phone number.  As a convention
        to facilitate automatic notification of the operator by
        the agent or network management station, the phone
        number, fax number or email address should be indicated
        by the URL schemes 'tel:', 'fax:' and 'mailto:',
        respectively.  If either the phone, fax, or email
        information is not available, then a line should not
        be included for this information.
        NOTE: For interoperability purposes, it is advisable to use
        email addresses formatted per [RFC2822] requirements.
        NOTE: The above description has been modified from RFC 1759
        for clarification."
::= { prtGeneralEntry 5 }

prtInputDefaultIndex OBJECT-TYPE
        SYNTAX     Integer32 (1..65535)
        MAX-ACCESS read-write
        STATUS     current
        DESCRIPTION
        "The value of prtInputIndex corresponding to the default input
        sub-unit: that is, this object selects the default source of
        input media."
::= { prtGeneralEntry 6 }

prtOutputDefaultIndex OBJECT-TYPE
        --  A range has been added to the SYNTAX clause that was not in
        --  RFC 1759.  Although this violates SNMP compatibility rules,
        --  it provides a more reasonable guide for SNMP managers.
        SYNTAX     Integer32 (1..65535)
        MAX-ACCESS read-write
        STATUS     current
        DESCRIPTION
        "The value of prtOutputIndex corresponding to the default
        output sub-unit; that is, this object selects the default
        output destination."
::= { prtGeneralEntry 7 }

prtMarkerDefaultIndex OBJECT-TYPE
        SYNTAX     Integer32 (1..65535)
        MAX-ACCESS read-write
        STATUS     current
        DESCRIPTION
        "The value of prtMarkerIndex corresponding to the
        default marker sub-unit; that is, this object selects the
        default marker."
::= { prtGeneralEntry 8 }

prtMediaPathDefaultIndex OBJECT-TYPE
        SYNTAX     Integer32 (1..65535)
        MAX-ACCESS read-write
        STATUS     current
        DESCRIPTION
        "The value of prtMediaPathIndex corresponding to
        the default media path; that is, the selection of the
        default media path."
::= { prtGeneralEntry 9 }

prtConsoleLocalization OBJECT-TYPE
        SYNTAX     Integer32 (1..65535)
        MAX-ACCESS read-write
        STATUS     current
        DESCRIPTION
        "The value of the prtLocalizationIndex corresponding to
        the language, country, and character set to be used for the
        console.  This localization applies both to the actual display
        on the console as well as the encoding of these console objects
        in management operations.  When an object's 'charset' is
        controlled by the value of prtConsoleLocalization, it MUST
        specify PrtConsoleDescriptionStringTC as its syntax.
        NOTE: The above description has been modified from RFC 1759
        for clarification."
::= { prtGeneralEntry 10 }

prtConsoleNumberOfDisplayLines OBJECT-TYPE
        SYNTAX     Integer32 (0..65535)
        MAX-ACCESS read-only
        STATUS     current
        DESCRIPTION
        "The number of lines on the printer's physical
        display.  This value is 0 if there are no lines on the
        physical display or if there is no physical display"
::= { prtGeneralEntry 11 }

prtConsoleNumberOfDisplayChars OBJECT-TYPE
        SYNTAX     Integer32 (0..65535)
        MAX-ACCESS read-only
        STATUS     current
        DESCRIPTION
        "The number of characters per line displayed on the physical
        display.  This value is 0 if there are no lines on the physical
        display or if there is no physical display"
::= { prtGeneralEntry 12 }

prtConsoleDisable OBJECT-TYPE
        -- In RFC 1759, the enumeration values were implicitly defined
        -- by this object.
        SYNTAX     PrtConsoleDisableTC
        MAX-ACCESS read-write
        STATUS     current
        DESCRIPTION
        "This value indicates how input is (or is not) accepted from
        the operator console.
        NOTE: The above description has been modified from RFC 1759
        for clarification."
::= { prtGeneralEntry 13 }

prtGeneralPrinterName OBJECT-TYPE
        SYNTAX     OCTET STRING (SIZE (0..127))
        MAX-ACCESS read-write
        STATUS     current
        DESCRIPTION
        "An administrator-specified name for this printer.  Depending
        upon implementation of this printer, the value of this object
        may or may not be same as the value for the MIB-II 'SysName'
        object."
::= { prtGeneralEntry 16 }

prtGeneralSerialNumber OBJECT-TYPE
        SYNTAX     OCTET STRING (SIZE (0..255))
        MAX-ACCESS read-write
        STATUS     current
        DESCRIPTION
        "A recorded serial number for this device that indexes some
        type device catalog or inventory.  This value is usually set by
        the device manufacturer but the MIB supports the option of
        writing for this object for site-specific administration of
        device inventory or tracking."
::= { prtGeneralEntry 17 }

prtAlertCriticalEvents OBJECT-TYPE
        SYNTAX     Counter32
        MAX-ACCESS read-only
        STATUS     current
        DESCRIPTION
        "A running counter of the number of critical alert events that
        have been recorded in the alert table.  The value of this object
        is RESET in the event of a power cycle operation (i.e., the
        value is not persistent."
::= { prtGeneralEntry 18 }

prtAlertAllEvents OBJECT-TYPE
        SYNTAX     Counter32
        MAX-ACCESS read-only
        STATUS     current
        DESCRIPTION
        "A running counter of the total number of alert event entries
        (critical and non-critical) that have been recorded in the
        alert table"
::= { prtGeneralEntry 19 }

prtStorageRefIndex OBJECT-TYPE
        -- NOTE: The range has been changed from RFC 1759 to be compatible
        -- with the defined range of hrDeviceIndex.
        SYNTAX     Integer32 (0..2147483647)
        MAX-ACCESS read-only
        STATUS     current
        DESCRIPTION
        "The value of the hrDeviceIndex of the printer device that this
        storageEntry is associated with."
::= { prtStorageRefEntry 2 }

prtDeviceRefIndex OBJECT-TYPE
        -- NOTE: The range has been changed from RFC 1759 to be compatible
        -- with the defined range of hrDeviceIndex.
        SYNTAX     Integer32 (0..2147483647)
        MAX-ACCESS read-only
        STATUS     current
        DESCRIPTION
        "The value of the hrDeviceIndex of the printer device that this
        deviceEntry is associated with."
::= { prtDeviceRefEntry 2 }

prtCoverDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "The manufacturer provided cover sub-mechanism name in the
        localization specified by prtGeneralCurrentLocalization."
::= { prtCoverEntry 2 }

prtCoverStatus  OBJECT-TYPE
        -- NOTE: In RFC 1759, the enumeration values were implicitly defined
        -- by this object and are now defined in the IANA-PRINTER-MIB.  The
        -- new TC has defined "coverOpen" and "coverClosed" to replace
        -- "doorOpen" and "doorClosed" in RFC 1759.  A name change is not
        -- formally allowed per SMI rules, but was agreed to by the WG group
        -- since a door has a more restrictive meaning than a cover and
        -- Cover group is intended to support doors as a subset of covers.
        SYNTAX     PrtCoverStatusTC
        MAX-ACCESS read-only
        STATUS     current
        DESCRIPTION
        "The status of this cover sub-unit."
::= { prtCoverEntry 3 }

prtLocalizationLanguage OBJECT-TYPE
        -- Note: The size is fixed, was incorrectly 0..2 in RFC 1759.
        SYNTAX     OCTET STRING (SIZE(2))
        MAX-ACCESS read-only
        STATUS     current
        DESCRIPTION
        "A two character language code from ISO 639.  Examples en,
        es, fr, de.  NOTE: These examples were shown as upper case in
        RFC 1759 and are now shown as lower case to agree with ISO 639."
::= { prtLocalizationEntry 2 }

prtLocalizationCountry OBJECT-TYPE
        -- Note: The size is fixed, was incorrectly 0..2 in RFC 1759.
        SYNTAX     OCTET STRING (SIZE(2))
        MAX-ACCESS read-only
        STATUS     current
        DESCRIPTION
        "A two character country code from ISO 3166, a blank string
        (two space characters) shall indicate that the country is not
        defined.  Examples: US, GB, FR, DE, ..."
::= { prtLocalizationEntry 3 }

prtLocalizationCharacterSet OBJECT-TYPE
        SYNTAX     IANACharset
        MAX-ACCESS read-only
        STATUS     current
        DESCRIPTION
        "The coded character set used for this localization."
::= { prtLocalizationEntry 4 }

prtInputType OBJECT-TYPE
        -- NOTE: In RFC 1759, the enumeration values were implicitly
        -- defined by this object.
        SYNTAX     PrtInputTypeTC
        MAX-ACCESS read-only
        STATUS     current
        DESCRIPTION
        "The type of technology (discriminated primarily according to
        feeder mechanism type) employed by the input sub-unit.  Note,
        the Input Class provides for a descriptor field to further
        qualify the other choice."
::= { prtInputEntry 2 }

prtInputDimUnit OBJECT-TYPE
        SYNTAX     PrtMediaUnitTC
        MAX-ACCESS read-only
        STATUS     current
        DESCRIPTION
        "The unit of measurement for use calculating and relaying
        dimensional values for this input sub-unit."
::= { prtInputEntry 3 }

prtInputMediaDimFeedDirDeclared OBJECT-TYPE
        -- NOTE: In RFC 1759, the range was not defined.
        SYNTAX     Integer32 (-2..2147483647)
        MAX-ACCESS read-write
        STATUS     current
        DESCRIPTION
        "This object provides the value of the declared dimension, in
        the feed direction, of the media that is (or, if empty, was or
        will be) in this input sub-unit.  The feed direction is the
        direction in which the media is fed on this sub-unit.  This
        dimension is measured in input sub-unit dimensional units
        (controlled by prtInputDimUnit, which uses PrtMediaUnitTC).  If
        this input sub-unit can reliably sense this value, the value is
        sensed by the printer and may not be changed by management
        requests.  Otherwise, the value may be changed.  The value (-1)
        means other and specifically means that this sub-unit places no
        restriction on this parameter.  The value (-2) indicates
        unknown."
::= { prtInputEntry 4 }

prtInputMediaDimXFeedDirDeclared OBJECT-TYPE
        -- NOTE: In RFC 1759, the range was not defined.
        SYNTAX     Integer32 (-2..2147483647)
        MAX-ACCESS read-write
        STATUS     current
        DESCRIPTION
        "This object provides the value of the declared dimension, in
        the cross feed direction, of the media that is (or, if empty,
        was or will be) in this input sub-unit.  The cross  feed
        direction is ninety degrees relative to the feed direction
        associated with this sub-unit.  This dimension is measured in
        input sub-unit dimensional units (controlled by
        prtInputDimUnit,which uses PrtMediaUnitTC).  If this input sub-
        unit can reliably sense this value, the value is sensed by the
        printer and may not be changed by management requests.
        Otherwise, the value may be changed.  The value (-1) means other
        and specifically means that this sub-unit places no restriction
        on this parameter.  The value (-2) indicates unknown."
::= { prtInputEntry 5 }

prtInputMediaDimFeedDirChosen OBJECT-TYPE
        -- NOTE: In RFC 1759, the range was not defined.
        SYNTAX     Integer32 (-2..2147483647)
        MAX-ACCESS read-only
        STATUS     current
        DESCRIPTION
        "The printer will act as if media of the chosen dimension (in
        the feed direction) is present in this input source.  Note that
        this value will be used even if the input tray is empty.  Feed
        dimension measurements are taken relative to the feed direction
        associated with that sub-unit and are in input sub-unit
        dimensional units (controlled by prtInputDimUnit, which uses
        PrtMediaUnitTC).  If the printer supports the declared
        dimension,the granted dimension is the same as the declared
        dimension.  If not, the granted dimension is set to the closest
        dimension that the printer supports when the declared dimension
        is set.  The value (-1) means other and specifically indicates
        that this sub-unit places no restriction on this parameter.  The
        value (-2)indicates unknown."
::= { prtInputEntry 6 }

prtInputMediaDimXFeedDirChosen OBJECT-TYPE
        -- NOTE: In RFC 1759, the range was not defined.
        SYNTAX     Integer32 (-2..2147483647)
        MAX-ACCESS read-only
        STATUS     current
        DESCRIPTION
        "The printer will act as if media of the chosen dimension (in
        the cross feed direction) is present in this input source.  Note
        that this value will be used even if the input tray is empty.
        The cross feed direction is ninety degrees relative to the feed
        direction associated with this sub-unit.  This dimension is
        measured in input sub-unit dimensional units (controlled by
        prtInputDimUnit, which uses PrtMediaUnitTC).  If the printer
        supports the declare dimension, the granted dimension is the
        same as the declared dimension.  If not, the granted dimension
        is set to the closest dimension that the printer supports when
        the declared dimension is set.  The value (-1) means other and
        specifically indicates that this sub-unit places no restriction
        on this parameter.  The value (-2) indicates unknown."
::= { prtInputEntry 7 }

prtInputCapacityUnit OBJECT-TYPE
        -- NOTE: In RFC 1759, the enumeration values were implicitly
        -- defined by this object.
        SYNTAX     PrtCapacityUnitTC
        MAX-ACCESS read-only
        STATUS     current
        DESCRIPTION
        "The unit of measurement for use in calculating and relaying
        capacity values for this input sub-unit."
::= { prtInputEntry 8 }

prtInputMaxCapacity OBJECT-TYPE
        -- NOTE: In RFC 1759, the range was not defined.
        SYNTAX     Integer32 (-2..2147483647)
        MAX-ACCESS read-write
        STATUS     current
        DESCRIPTION
        "The maximum capacity of the input sub-unit in input sub-unit
        capacity units (PrtCapacityUnitTC).  There is no convention
        associated with the media itself so this value reflects claimed
        capacity.  If this input sub-unit can reliably sense this value,
        the value is sensed by the printer and may not be changed by
        management requests; otherwise, the value may be written (by a
        Remote Control Panel or a Management Application). The value
        (-1) means other and specifically indicates that the sub-unit
        places no restrictions on this parameter.  The value (-2) means
        unknown."
::= { prtInputEntry 9 }

prtInputCurrentLevel OBJECT-TYPE
        -- NOTE: In RFC 1759, the range was not defined.
        SYNTAX     Integer32 (-3..2147483647)    -- in capacity units
        -- (PrtCapacityUnitTC).
        MAX-ACCESS read-write
        STATUS     current
        DESCRIPTION
        "The current capacity of the input sub-unit in input sub-unit
        capacity units (PrtCapacityUnitTC).  If this input sub-unit can
        reliably sense this value, the value is sensed by the printer
        and may not be changed by management requests; otherwise, the
        value may be written (by a Remote Control Panel or a Management
        Application).  The value (-1) means other and specifically
        indicates that the sub-unit places no restrictions on this
        parameter.  The value (-2) means unknown.  The value (-3) means
        that the printer knows that at least one unit remains."
::= { prtInputEntry 10 }

prtInputStatus OBJECT-TYPE
        SYNTAX     PrtSubUnitStatusTC
        MAX-ACCESS read-only
        STATUS     current
        DESCRIPTION
        "The current status of this input sub-unit."
::= { prtInputEntry 11 }

prtInputMediaName OBJECT-TYPE
        SYNTAX     OCTET STRING (SIZE(0..63))
        MAX-ACCESS read-write
        STATUS     current
        DESCRIPTION
        "A description of the media contained in this input sub-unit;
        This description is to be used by a client to format and
        Localize a string for display to a human operator.  This
        description is not processed by the printer.  It is used to
        provide information not expressible in terms of the other
        media attributes (e.g., prtInputMediaDimFeedDirChosen,
        prtInputMediaDimXFeedDirChosen, prtInputMediaWeight,
        prtInputMediaType)."
        -- The following reference was not included in RFC 1759.
        REFERENCE
        "The PWG Standardized Media Names specification [PWGMEDIA]
        contains the recommended values for this object.  See also
        RFC 3805 Appendix C,'Media Names', which lists the values
        Of standardized media names defined in ISO/IEC 10175."
::= { prtInputEntry 12 }

prtInputName OBJECT-TYPE
        SYNTAX     OCTET STRING (SIZE(0..63))
        MAX-ACCESS read-write
        STATUS     current
        DESCRIPTION
        "The name assigned to this input sub-unit."
::= { prtInputEntry 13 }

prtInputVendorName OBJECT-TYPE
        SYNTAX     OCTET STRING (SIZE(0..63))
        MAX-ACCESS read-only
        STATUS     current
        DESCRIPTION
        "The vendor name of this input sub-unit."
::= { prtInputEntry 14 }

prtInputModel OBJECT-TYPE
        SYNTAX     OCTET STRING (SIZE(0..63))
        MAX-ACCESS read-only
        STATUS     current
        DESCRIPTION
        "The model name of this input sub-unit."
::= { prtInputEntry 15 }

prtInputVersion OBJECT-TYPE
        SYNTAX     OCTET STRING (SIZE(0..63))
        MAX-ACCESS read-only
        STATUS     current
        DESCRIPTION
        "The version of this input sub-unit."
::= { prtInputEntry 16 }

prtInputSerialNumber OBJECT-TYPE
        SYNTAX     OCTET STRING (SIZE(0..32))
        MAX-ACCESS read-only
        STATUS     current
        DESCRIPTION
        "The serial number assigned to this input sub-unit."
::= { prtInputEntry 17 }

prtInputDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A free-form text description of this input sub-unit in the
        localization specified by  prtGeneralCurrentLocalization."
::= { prtInputEntry 18 }

prtInputSecurity OBJECT-TYPE
        SYNTAX     PresentOnOff
        MAX-ACCESS read-write
        STATUS     current
        DESCRIPTION
        "Indicates if this input sub-unit has some security associated
        with it."
::= { prtInputEntry 19 }

prtInputMediaWeight  OBJECT-TYPE
        -- NOTE: In RFC 1759, the range was not defined.
        SYNTAX     Integer32 (-2..2147483647)
        MAX-ACCESS read-write
        STATUS     current
        DESCRIPTION
        "The weight of the medium associated with this input sub-unit
        in grams / per meter squared.  The value (-2) means unknown."
::= { prtInputEntry 20 }

prtInputMediaType OBJECT-TYPE
        SYNTAX     OCTET STRING (SIZE(0..63))
        MAX-ACCESS read-write
        STATUS     current
        DESCRIPTION
        "The name of the type of medium associated with this input sub
        unit.  This name need not be processed by the printer; it might
        simply be displayed to an operator.
        NOTE: The above description has been modified from RFC 1759."
        -- The following reference was not included in RFC 1759.
        REFERENCE
        "The PWG Standardized Media Names specification [PWGMEDIA],
        section 3 Media Type Names, contains the recommended values for
        this object.  Implementers may add additional string values.
        The naming conventions in ISO 9070 are recommended in order to
        avoid potential name clashes."
::= { prtInputEntry 21 }

prtInputMediaColor OBJECT-TYPE
        SYNTAX     OCTET STRING (SIZE(0..63))
        MAX-ACCESS read-write
        STATUS     current
        DESCRIPTION
        "The name of the color of the medium associated with
        this input sub-unit using standardized string values.
        NOTE: The above description has been modified from RFC 1759."
        -- The following reference was not included in RFC 1759.
        REFERENCE
        "The PWG Standardized Media Names specification [PWGMEDIA],
        section 4 Media Color Names, contains the recommended values
        for this object.  Implementers may add additional string values.
        The naming conventions in ISO 9070 are recommended in order to
        avoid potential name clashes."
::= { prtInputEntry 22 }

prtInputMediaFormParts OBJECT-TYPE
        -- NOTE: In RFC 1759, the range was not defined.
        SYNTAX     Integer32 (-2..2147483647)
        MAX-ACCESS read-write
        STATUS     current
        DESCRIPTION
        "The number of parts associated with the medium
        associated with this input sub-unit if the medium is a
        multi-part form.  The value (-1) means other and
        specifically indicates that the device places no
        restrictions on this parameter.  The value (-2) means
        unknown."
::= { prtInputEntry 23 }

prtInputMediaLoadTimeout OBJECT-TYPE
        SYNTAX     Integer32 (-2..2147483647)
        MAX-ACCESS read-write
        STATUS     current
        DESCRIPTION
        "When the printer is not able to print due to a subunit being
        empty or the requested media must be manually loaded, the
        printer will wait for the duration (in seconds) specified by
        this object.  Upon expiration of the time-out, the printer will
        take the action specified by prtInputNextIndex.
        The event which causes the printer to enter the waiting state
        is product specific.  If the printer is not waiting for manually
        fed media, it may switch from an empty subunit to a different
        subunit without waiting for the time-out to expire.
        A value of (-1) implies 'other' or 'infinite' which translates
        to 'wait forever'.  The action which causes printing to continue
        is product specific.  A value of (-2) implies 'unknown'."
::= { prtInputEntry 24 }

prtOutputType OBJECT-TYPE
        -- NOTE: In RFC 1759, the enumeration values were implicitly defined
        -- by this object.
        SYNTAX     PrtOutputTypeTC
        MAX-ACCESS read-only
        STATUS     current
        DESCRIPTION
        "The type of technology supported by this output sub-unit."
::= { prtOutputEntry 2 }

prtOutputCapacityUnit OBJECT-TYPE
        SYNTAX     PrtCapacityUnitTC
        MAX-ACCESS read-only
        STATUS     current
        DESCRIPTION
        "The unit of measurement for use in calculating and relaying
        capacity values for this output sub-unit."
::= { prtOutputEntry 3 }

prtOutputMaxCapacity OBJECT-TYPE
        -- NOTE: In RFC 1759, the range was not defined.
        SYNTAX     Integer32 (-2..2147483647)
        MAX-ACCESS read-write
        STATUS     current
        DESCRIPTION
        "The maximum capacity of this output sub-unit in output sub-
        unit capacity units (PrtCapacityUnitTC).  There is no convention
        associated with the media itself so this value essentially
        reflects claimed capacity.  If this output sub-unit can reliably
        sense this value, the value is sensed by the printer and may
        not be changed by management requests; otherwise, the value may
        be written (by a Remote Control Panel or a Management
        Application).  The value (-1) means other and specifically
        indicates that the sub-unit places no restrictions on this
        parameter.  The value (-2) means unknown."
::= { prtOutputEntry 4 }

prtOutputRemainingCapacity OBJECT-TYPE
        -- NOTE: In RFC 1759, the range was not defined.
        SYNTAX     Integer32 (-3..2147483647)
        MAX-ACCESS read-write
        STATUS     current
        DESCRIPTION
        "The remaining capacity of the possible output sub-unit
        capacity in output sub-unit capacity units
        (PrtCapacityUnitTC)of this output sub-unit.  If this output sub-
        unit can reliably sense this value, the value is sensed by the
        printer and may not be modified by management requests;
        otherwise, the value may be written (by a Remote Control Panel
        or a Management Application).  The value (-1) means other and
        specifically indicates that the sub-unit places no restrictions
        on this parameter.  The value (-2) means unknown.  The value
        (-3) means that the printer knows that there remains capacity
        for at least one unit."
::= { prtOutputEntry 5 }

prtOutputStatus OBJECT-TYPE
        SYNTAX     PrtSubUnitStatusTC
        MAX-ACCESS read-only
        STATUS     current
        DESCRIPTION
        "The current status of this output sub-unit."
::= { prtOutputEntry 6 }

prtOutputName OBJECT-TYPE
        SYNTAX     OCTET STRING (SIZE(0..63))
        MAX-ACCESS read-write
        STATUS     current
        DESCRIPTION
        "The name assigned to this output sub-unit."
::= { prtOutputEntry 7 }

prtOutputVendorName OBJECT-TYPE
        SYNTAX     OCTET STRING (SIZE(0..63))
        MAX-ACCESS read-only
        STATUS     current
        DESCRIPTION
        "The vendor name of this output sub-unit."
::= { prtOutputEntry 8 }

prtOutputModel OBJECT-TYPE
        SYNTAX     OCTET STRING (SIZE(0..63))
        MAX-ACCESS read-only
        STATUS     current
        DESCRIPTION
        "The model name assigned to this output sub-unit.
        NOTE: The above description has been modified from RFC 1759
        for clarification."
::= { prtOutputEntry 9 }

prtOutputVersion OBJECT-TYPE
        SYNTAX     OCTET STRING (SIZE(0..63))
        MAX-ACCESS read-only
        STATUS     current
        DESCRIPTION
        "The version of this output sub-unit."
::= { prtOutputEntry 10 }

prtOutputSerialNumber OBJECT-TYPE
        SYNTAX     OCTET STRING (SIZE(0..63))
        MAX-ACCESS read-only
        STATUS     current
        DESCRIPTION
        "The serial number assigned to this output sub-unit."
::= { prtOutputEntry 11 }

prtOutputDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A free-form text description of this output sub-unit in the
        localization specified by prtGeneralCurrentLocalization."
::= { prtOutputEntry 12 }

prtOutputSecurity OBJECT-TYPE
        SYNTAX     PresentOnOff
        MAX-ACCESS read-write
        STATUS     current
        DESCRIPTION
        "Indicates if this output sub-unit has some security associated
        with it and if that security is enabled or not."
::= { prtOutputEntry 13 }

prtOutputDimUnit OBJECT-TYPE
        SYNTAX     PrtMediaUnitTC
        MAX-ACCESS read-only
        STATUS     current
        DESCRIPTION
        "The unit of measurement for use in calculating and relaying
        dimensional values for this output sub-unit."
::= { prtOutputEntry 14 }

prtOutputMaxDimFeedDir OBJECT-TYPE
        -- NOTE: In RFC 1759, the range was not defined.
        SYNTAX     Integer32 (-2..2147483647)
        MAX-ACCESS read-write
        STATUS     current
        DESCRIPTION
        "The maximum dimensions supported by this output sub-unit
        for measurements taken parallel relative to the feed
        direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 15 }

prtOutputMaxDimXFeedDir OBJECT-TYPE
        -- NOTE: In RFC 1759, the range was not defined.
        SYNTAX     Integer32 (-2..2147483647)
        MAX-ACCESS read-write
        STATUS     current
        DESCRIPTION
        "The maximum dimensions supported by this output sub-unit
        for measurements taken ninety degrees relative to the
        feed direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 16 }

prtOutputMinDimFeedDir OBJECT-TYPE
        -- NOTE: In RFC 1759, the range was not defined.
        SYNTAX     Integer32 (-2..2147483647)
        MAX-ACCESS read-write
        STATUS     current
        DESCRIPTION
        "The minimum dimensions supported by this output sub-unit
        for measurements taken parallel relative to the feed
        direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 17 }

prtOutputMinDimXFeedDir OBJECT-TYPE
        -- NOTE: In RFC 1759, the range was not defined.
        SYNTAX     Integer32 (-2..2147483647)
        MAX-ACCESS read-write
        STATUS     current
        DESCRIPTION
        "The minimum dimensions supported by this output sub-unit
        for measurements taken ninety degrees relative to the
        feed direction associated with that sub-unit in output
        sub-unit dimensional units (controlled by prtOutputDimUnit,
        which uses PrtMediaUnitTC).  If this output sub-unit can
        reliably sense this value, the value is sensed by the printer
        and may not be changed with management protocol operations.
        The value (-1) means other and specifically indicates that the
        sub-unit places no restrictions on this parameter.  The value
        (-2) means unknown.
        NOTE: The above description has been modified from RFC 1759
        for clarification and to explain the purpose of (-1) and (-2)."
::= { prtOutputEntry 18 }

prtOutputStackingOrder OBJECT-TYPE
        --  NOTE: In RFC 1759, the enumeration values were implicitly
        --  defined by this object.
        SYNTAX     PrtOutputStackingOrderTC
        MAX-ACCESS read-write
        STATUS     current
        DESCRIPTION
        "The current state of the stacking order for the
        associated output sub-unit. 'FirstToLast' means
        that as pages are output the front of the next page is
        placed against the back of the previous page.
        'LasttoFirst' means that as pages are output the back
        of the next page is placed against the front of the
        previous page."
::= { prtOutputEntry 19 }

prtOutputPageDeliveryOrientation OBJECT-TYPE
        --  NOTE: In RFC 1759, the enumeration values were implicitly
        --  defined by this object.
        SYNTAX     PrtOutputPageDeliveryOrientationTC
        MAX-ACCESS read-write
        STATUS     current
        DESCRIPTION
        "The reading surface that will be 'up' when pages are
        delivered to the associated output sub-unit.  Values are
        faceUp and faceDown.  (Note: interpretation of these
        values is in general context-dependent based on locale;
        presentation of these values to an end-user should be
        normalized to the expectations of the user)."
::= { prtOutputEntry 20 }

prtOutputBursting OBJECT-TYPE
        SYNTAX     PresentOnOff
        MAX-ACCESS read-write
        STATUS     current
        DESCRIPTION
        "This object indicates that the outputting sub-unit supports
        bursting, and if so, whether the feature is enabled.  Bursting
        is the process by which continuous media is separated into
        individual sheets, typically by bursting along pre-formed
        perforations."
::= { prtOutputEntry 21 }

prtOutputDecollating OBJECT-TYPE
        SYNTAX     PresentOnOff
        MAX-ACCESS read-write
        STATUS     current
        DESCRIPTION
        "This object indicates that the output supports decollating,
        and if so, whether the feature is enabled.  Decollating is the
        process by which the individual parts within a multi-part form
        are separated and sorted into separate stacks for each part."
::= { prtOutputEntry 22 }

prtOutputPageCollated OBJECT-TYPE
        SYNTAX     PresentOnOff
        MAX-ACCESS read-write
        STATUS     current
        DESCRIPTION
        "This object indicates that the output sub-unit supports page
        collation, and if so, whether the feature is enabled.  See RFC
        3805 Appendix A, Glossary Of Terms, for definition of how this
        document defines collation.
        NOTE: The above description has been modified from RFC 1759
        for clarification."
::= { prtOutputEntry 23 }

prtOutputOffsetStacking OBJECT-TYPE
        SYNTAX     PresentOnOff
        MAX-ACCESS read-write
        STATUS     current
        DESCRIPTION
        "This object indicates that the output supports offset
        stacking,and if so, whether the feature is enabled.  See RFC
        3805 Appendix A, Glossary Of Terms,  for how Offset Stacking is
        defined by this document.
        NOTE: The above description has been modified from RFC 1759
        for clarification."
::= { prtOutputEntry 24 }

prtMarkerMarkTech OBJECT-TYPE
        --  NOTE: In RFC 1759, the enumeration values were implicitly
        --  defined by this object.
        SYNTAX     PrtMarkerMarkTechTC
        MAX-ACCESS read-only
        STATUS     current
        DESCRIPTION
        "The type of marking technology used for this marking
        sub-unit."
::= { prtMarkerEntry 2 }

prtMarkerCounterUnit OBJECT-TYPE
        --  NOTE: In RFC 1759, the enumeration values were implicitly
        --  defined by this object.
        SYNTAX     PrtMarkerCounterUnitTC
        MAX-ACCESS read-only
        STATUS     current
        DESCRIPTION
        "The unit that will be used by the printer when reporting
        counter values for this marking sub-unit.  The time units of
        measure are provided for a device like a strip recorder that
        does not or cannot track the physical dimensions of the media
        and does not use characters, lines or sheets."
::= { prtMarkerEntry 3 }

prtMarkerLifeCount OBJECT-TYPE
        SYNTAX     Counter32
        MAX-ACCESS read-only
        STATUS     current
        DESCRIPTION
        "The count of the number of units of measure counted during the
        life of printer using units of measure as specified by
        prtMarkerCounterUnit.
        Note: This object should be implemented as a persistent object
        with a reliable value throughout the lifetime of the printer."
::= { prtMarkerEntry 4 }

prtMarkerPowerOnCount OBJECT-TYPE
        SYNTAX     Counter32
        MAX-ACCESS read-only
        STATUS     current
        DESCRIPTION
        "The count of the number of units of measure counted since the
        equipment was most recently powered on using units of measure
        as specified by prtMarkerCounterUnit."
::= { prtMarkerEntry 5 }

prtMarkerProcessColorants OBJECT-TYPE
        SYNTAX     Integer32 (0..65535)
        MAX-ACCESS read-only
        STATUS     current
        DESCRIPTION
        "The number of process colors supported by this marker.  A
        process color of 1 implies monochrome.  The value of this
        object and prtMarkerSpotColorants cannot both be 0.  The value
        of prtMarkerProcessColorants must be 0 or greater.
        NOTE: The above description has been modified from RFC 1759
        for clarification."
::= { prtMarkerEntry 6 }

prtMarkerSpotColorants OBJECT-TYPE
        SYNTAX     Integer32 (0..65535)
        MAX-ACCESS read-only
        STATUS     current
        DESCRIPTION
        "The number of spot colors supported by this marker.  The value
        of this object and prtMarkerProcessColorants cannot both be 0.
        Must be 0 or greater.
        NOTE: The above description has been modified from RFC 1759
        for clarification."
::= { prtMarkerEntry 7 }

prtMarkerAddressabilityUnit OBJECT-TYPE
        --  NOTE: In RFC 1759, the enumeration values were implicitly
        --  defined by this object.
        SYNTAX     PrtMarkerAddressabilityUnitTC
        MAX-ACCESS read-only
        STATUS     current
        DESCRIPTION
        "The unit of measure of distances, as applied to the marker's
        resolution.
        NOTE: The above description has been modified from RFC 1759
        for clarification."
::= { prtMarkerEntry 8 }

prtMarkerAddressabilityFeedDir OBJECT-TYPE
        -- NOTE: In RFC 1759, the range was not defined.
        SYNTAX     Integer32 (-2..2147483647)
        MAX-ACCESS read-only
        STATUS     current
        DESCRIPTION
        "The maximum number of addressable marking positions in the
        feed direction per 10000 units of measure specified by
        prtMarkerAddressabilityUnit.  A value of (-1) implies 'other'
        or 'infinite' while a value of (-2) implies 'unknown'.
        NOTE: The above description has been modified from RFC 1759
        for clarification."
::= { prtMarkerEntry 9 }

prtMarkerAddressabilityXFeedDir OBJECT-TYPE
        -- NOTE: In RFC 1759, the range was not defined.
        SYNTAX     Integer32 (-2..2147483647)
        MAX-ACCESS read-only
        STATUS     current
        DESCRIPTION
        "The maximum number of addressable marking positions in the
        cross feed direction in 10000 units of measure specified by
        prtMarkerAddressabilityUnit.  A value of (-1) implies 'other'
        or 'infinite' while a value of (-2) implies 'unknown'.
        NOTE: The above description has been modified from RFC 1759
        for clarification."
::= { prtMarkerEntry 10 }

prtMarkerNorthMargin OBJECT-TYPE
        -- NOTE: In RFC 1759, the range was not defined.
        SYNTAX     Integer32 (-2..2147483647)
        MAX-ACCESS read-only
        STATUS     current
        DESCRIPTION
        "The margin, in units identified by prtMarkerAddressabilityUnit,
        from the leading edge of the medium as the medium flows through
        the marking engine with the side to be imaged facing the
        observer.  The leading edge is the North edge and the other
        edges are defined by the normal compass layout of  directions
        with the compass facing the observer.  Printing within the area
        bounded by all four margins is guaranteed for all interpreters.
        The value (-2) means unknown."
::= { prtMarkerEntry 11 }

prtMarkerSouthMargin OBJECT-TYPE
        -- NOTE: In RFC 1759, the range was not defined.
        SYNTAX     Integer32 (-2..2147483647)
        MAX-ACCESS read-only
        STATUS     current
        DESCRIPTION
        "The margin from the South edge  (see prtMarkerNorthMargin) of
        the medium in units identified by prtMarkerAddressabilityUnit.
        Printing within the area bounded by all four margins  is
        guaranteed for all interpreters.  The value (-2) means unknown."
::= { prtMarkerEntry 12 }

prtMarkerWestMargin OBJECT-TYPE
        -- NOTE: In RFC 1759, the range was not defined.
        SYNTAX     Integer32 (-2..2147483647)
        MAX-ACCESS read-only
        STATUS     current
        DESCRIPTION
        "The margin from the West edge (see prtMarkerNorthMargin) of
        the medium in units identified by prtMarkerAddressabilityUnit.
        Printing within the area bounded by all four margins is
        guaranteed for all interpreters.  The value (-2) means unknown."
::= { prtMarkerEntry 13 }

prtMarkerEastMargin OBJECT-TYPE
        -- NOTE: In RFC 1759, the range was not defined.
        SYNTAX     Integer32 (-2..2147483647)
        MAX-ACCESS read-only
        STATUS     current
        DESCRIPTION
        "The margin from the East edge (see prtMarkerNorthMargin) of
        the medium in units identified by prtMarkerAddressabilityUnit.
        Printing within the area bounded by all four margins is
        guaranteed for all interpreters.  The value (-2) means unknown."
::= { prtMarkerEntry 14 }

prtMarkerStatus OBJECT-TYPE
        SYNTAX     PrtSubUnitStatusTC
        MAX-ACCESS read-only
        STATUS     current
        DESCRIPTION
        "The current status of this marker sub-unit."
::= { prtMarkerEntry 15 }

prtMarkerSuppliesMarkerIndex OBJECT-TYPE
        SYNTAX     Integer32 (0..65535)
        MAX-ACCESS read-only
        STATUS     current
        DESCRIPTION
        "The value of prtMarkerIndex corresponding to the marking sub
        unit with which this marker supply sub-unit is associated."
::= { prtMarkerSuppliesEntry 2 }

prtMarkerSuppliesColorantIndex OBJECT-TYPE
        SYNTAX     Integer32 (0..65535)
        MAX-ACCESS read-only
        STATUS     current
        DESCRIPTION
        "The value of prtMarkerColorantIndex corresponding to the
        colorant with which this marker supply sub-unit is associated.
        This value shall be 0 if there is no colorant table or if this
        supply does not depend on a single specified colorant.
        NOTE: The above description has been modified from RFC 1759
        for clarification."
::= { prtMarkerSuppliesEntry 3 }

prtMarkerSuppliesClass OBJECT-TYPE
        --  NOTE: In RFC 1759, the enumeration values were implicitly
        --  defined by this object.
        SYNTAX     PrtMarkerSuppliesClassTC
        MAX-ACCESS read-only
        STATUS     current
        DESCRIPTION
        "Indicates whether this supply entity represents a supply that
        is consumed or a receptacle that is filled.
        NOTE: The above description has been modified from RFC 1759
        for clarification."
::= { prtMarkerSuppliesEntry 4 }

prtMarkerSuppliesType OBJECT-TYPE
        --  NOTE: In RFC 1759, the enumeration values were implicitly
        --  defined by this object.
        SYNTAX     PrtMarkerSuppliesTypeTC
        MAX-ACCESS read-only
        STATUS     current
        DESCRIPTION
        "The type of this supply."
::= { prtMarkerSuppliesEntry 5 }

prtMarkerSuppliesDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "The description of this supply container/receptacle in the
        localization specified by prtGeneralCurrentLocalization."
::= { prtMarkerSuppliesEntry 6 }

prtMarkerSuppliesSupplyUnit OBJECT-TYPE
        --  NOTE: In RFC 1759, the enumeration values were implicitly
        --  defined by this object.
        SYNTAX     PrtMarkerSuppliesSupplyUnitTC
        MAX-ACCESS read-only
        STATUS     current
        DESCRIPTION
        "Unit of measure of this marker supply container/receptacle.
        NOTE: The above description has been modified from RFC 1759
        for clarification."
::= { prtMarkerSuppliesEntry 7 }

prtMarkerSuppliesMaxCapacity OBJECT-TYPE
        -- NOTE: In RFC 1759, the range was not defined.
        SYNTAX     Integer32 (-2..2147483647)
        MAX-ACCESS read-write
        STATUS     current
        DESCRIPTION
        "The maximum capacity of this supply container/receptacle
        expressed in prtMarkerSuppliesSupplyUnit.  If this supply
        container/receptacle can reliably sense this value, the value
        is reported by the printer and is read-only; otherwise, the
        value may be written (by a Remote Control Panel or a Management
        Application).  The value (-1) means other and specifically
        indicates that the sub-unit places no restrictions on this
        parameter.  The value (-2) means unknown."
::= { prtMarkerSuppliesEntry 8 }

prtMarkerSuppliesLevel OBJECT-TYPE
        -- NOTE: In RFC 1759, the range was not defined.
        SYNTAX     Integer32 (-3..2147483647)
        MAX-ACCESS read-write
        STATUS     current
        DESCRIPTION
        "The current level if this supply is a container; the remaining
        space if this supply is a receptacle.  If this supply
        container/receptacle can reliably sense this value, the value
        is reported by the printer and is read-only; otherwise, the
        value may be written (by a Remote Control Panel or a Management
        Application).  The value (-1) means other and specifically
        indicates that the sub-unit places no restrictions on this
        parameter.  The value (-2) means unknown.  A value of (-3) means
        that the printer knows that there is some supply/remaining
        space, respectively."
::= { prtMarkerSuppliesEntry 9 }

prtMarkerColorantMarkerIndex OBJECT-TYPE
        SYNTAX     Integer32 (0..65535)
        MAX-ACCESS read-only
        STATUS     current
        DESCRIPTION
        "The value of prtMarkerIndex corresponding to the marker sub
        unit with which this colorant entry is associated."
::= { prtMarkerColorantEntry 2 }

prtMarkerColorantRole OBJECT-TYPE
        --  NOTE: In RFC 1759, the enumeration values were implicitly
        --  defined by this object.
        SYNTAX     PrtMarkerColorantRoleTC
        MAX-ACCESS read-only
        STATUS     current
        DESCRIPTION
        "The role played by this colorant."
::= { prtMarkerColorantEntry 3 }

prtMarkerColorantValue OBJECT-TYPE
        -- NOTE: The string length range has been increased from RFC 1759.
        SYNTAX     OCTET STRING (SIZE(0..255))
        MAX-ACCESS read-only
        STATUS     current
        DESCRIPTION
        "The name of the color of this colorant using standardized
        string names from ISO 10175 (DPA) and ISO 10180 (SPDL) such as:
        other
        unknown
        white
        red
        green
        blue
        cyan
        magenta
        yellow
        black
        Implementers may add additional string values.  The naming
        conventions in ISO 9070 are recommended in order to avoid
        potential name clashes"
::= { prtMarkerColorantEntry 4 }

prtMarkerColorantTonality OBJECT-TYPE
        -- NOTE: In RFC 1759, the range was not defined.
        SYNTAX     Integer32 (2..2147483647)
        MAX-ACCESS read-only
        STATUS     current
        DESCRIPTION
        "The distinct levels of tonality realizable by a marking sub
        unit when using this colorant.  This value does not include the
        number of levels of tonal difference that an interpreter can
        obtain by techniques such as half toning.  This value must be at
        least 2."
::= { prtMarkerColorantEntry 5 }

prtMediaPathMaxSpeedPrintUnit OBJECT-TYPE
        --  NOTE: In RFC 1759, the enumeration values were implicitly
        --  defined by this object.
        SYNTAX PrtMediaPathMaxSpeedPrintUnitTC
        MAX-ACCESS read-only
        STATUS     current
        DESCRIPTION
        "The unit of measure used in specifying the speed of all media
        paths in the printer."
::= { prtMediaPathEntry 2 }

prtMediaPathMediaSizeUnit OBJECT-TYPE
        SYNTAX     PrtMediaUnitTC
        MAX-ACCESS read-only
        STATUS     current
        DESCRIPTION
        "The units of measure of media size for use in calculating and
        relaying dimensional values for all media paths in the
        printer."
::= { prtMediaPathEntry 3 }

prtMediaPathMaxSpeed OBJECT-TYPE
        -- NOTE: In RFC 1759, the range was not defined.
        SYNTAX     Integer32 (-2..2147483647)
        MAX-ACCESS read-only
        STATUS     current
        DESCRIPTION
        "The maximum printing speed of this media path expressed in
        prtMediaPathMaxSpeedUnit's.  A value of (-1) implies 'other'."
::= { prtMediaPathEntry 4 }

prtMediaPathMaxMediaFeedDir OBJECT-TYPE
        -- NOTE: In RFC 1759, the range was not defined.
        SYNTAX     Integer32 (-2..2147483647)
        MAX-ACCESS read-only
        STATUS     current
        DESCRIPTION
        "The maximum physical media size in the feed direction of this
        media path expressed in units of measure specified by
        PrtMediaPathMediaSizeUnit.  A value of (-1) implies 'unlimited'
        a value of (-2) implies 'unknown'.
        NOTE: The above description has been modified from RFC 1759
        for clarification."
::= { prtMediaPathEntry 5 }

prtMediaPathMaxMediaXFeedDir OBJECT-TYPE
        -- NOTE: In RFC 1759, the range was not defined.
        SYNTAX     Integer32 (-2..2147483647)
        MAX-ACCESS read-only
        STATUS     current
        DESCRIPTION
        "The maximum physical media size across the feed direction of
        this media path expressed in units of measure specified by
        prtMediaPathMediaSizeUnit.  A value of (-2) implies 'unknown'.
        NOTE: The above description has been modified from RFC 1759
        for clarification."
::= { prtMediaPathEntry 6 }

prtMediaPathMinMediaFeedDir OBJECT-TYPE
        -- NOTE: In RFC 1759, the range was not defined.
        SYNTAX     Integer32 (-2..2147483647)
        MAX-ACCESS read-only
        STATUS     current
        DESCRIPTION
        "The minimum physical media size in the feed direction of this
        media path expressed in units of measure specified by
        prtMediaPathMediaSizeUnit.  A value of (-2) implies 'unknown'.
        NOTE: The above description has been modified from RFC 1759
        for clarification."
::= { prtMediaPathEntry 7 }

prtMediaPathMinMediaXFeedDir OBJECT-TYPE
        -- NOTE: In RFC 1759, the range was not defined.
        SYNTAX     Integer32 (-2..2147483647)
        MAX-ACCESS read-only
        STATUS     current
        DESCRIPTION
        "The minimum physical media size across the feed direction of
        this media path expressed in units of measure specified by
        prtMediaPathMediaSizeUnit.  A value of (-2) implies 'unknown'.
        NOTE: The above description has been modified from RFC 1759
        for clarification."
::= { prtMediaPathEntry 8 }

prtMediaPathType OBJECT-TYPE
        --  NOTE: In RFC 1759, the enumeration values were implicitly
        --  defined by this object.
        SYNTAX     PrtMediaPathTypeTC
        MAX-ACCESS read-only
        STATUS     current
        DESCRIPTION
        "The type of the media path for this media path."
::= { prtMediaPathEntry 9 }

prtMediaPathDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "The manufacturer-provided description of this media path in
        the localization specified by prtGeneralCurrentLocalization."
::= { prtMediaPathEntry 10 }

prtMediaPathStatus OBJECT-TYPE
        SYNTAX     PrtSubUnitStatusTC
        MAX-ACCESS read-only
        STATUS     current
        DESCRIPTION
        "The current status of this media path."
::= { prtMediaPathEntry 11 }

prtChannelType OBJECT-TYPE
        --  NOTE: In RFC 1759, the enumeration values were implicitly
        --  defined by this object.
        SYNTAX     PrtChannelTypeTC
        MAX-ACCESS read-only
        STATUS     current
        DESCRIPTION
        "The type of this print data channel.  This object provides the
        linkage to ChannelType-specific groups that may (conceptually)
        extend the prtChannelTable with additional details about that
        channel."
::= { prtChannelEntry 2 }

prtChannelProtocolVersion OBJECT-TYPE
        SYNTAX     OCTET STRING (SIZE(0..63))
        MAX-ACCESS read-only
        STATUS     current
        DESCRIPTION
        "The version of the protocol used on this channel.  The format
        used for version numbering depends on prtChannelType."
::= { prtChannelEntry 3 }

prtChannelCurrentJobCntlLangIndex OBJECT-TYPE
        -- NOTE: In RFC 1759, the range was not defined.
        SYNTAX     Integer32 (0..65535)
        MAX-ACCESS read-write
        STATUS     current
        DESCRIPTION
        "The value of prtInterpreterIndex corresponding to the Control
        Language Interpreter for this channel.  This interpreter defines
        the syntax used for control functions, such as querying or
        changing environment variables and identifying job boundaries
        (e.g., PJL, PostScript, NPAP).  A value of zero indicates that
        there is no current Job Control Language Interpreter for this
        channel.
        NOTE: The above description has been modified from RFC 1759
        for clarification."
::= { prtChannelEntry 4 }

prtChannelDefaultPageDescLangIndex OBJECT-TYPE
        -- NOTE: In RFC 1759, the range was not defined.
        SYNTAX     Integer32 (0..65535)
        MAX-ACCESS read-write
        STATUS     current
        DESCRIPTION
        "The value of prtInterpreterIndex corresponding to the Page
        Description Language Interpreter for this channel.  This
        interpreter defines the default Page Description Language
        interpreter to be used for the print data unless the Control
        Language is used to select a specific interpreter (e.g., PCL,
        PostScript Language, auto-sense).  A value of zero indicates
        that there is no default page description language interpreter
        for this channel.
        NOTE: The above description has been modified from RFC 1759
        for clarification."
::= { prtChannelEntry 5 }

prtChannelState OBJECT-TYPE
        --  NOTE: In RFC 1759, the enumeration values were implicitly
        --  defined by this object.
        SYNTAX     PrtChannelStateTC
        MAX-ACCESS read-write
        STATUS     current
        DESCRIPTION
        "The state of this print data channel.  The value determines
        whether control information and print data is allowed through
        this channel or not."
::= { prtChannelEntry 6 }

prtChannelIfIndex OBJECT-TYPE
        SYNTAX     InterfaceIndexOrZero   -- Was Integer32 in RFC 1759.
        MAX-ACCESS read-write
        STATUS     current
        DESCRIPTION
        "The value of ifIndex in the ifTable; see the Interfaces Group
        MIB [RFC2863] which corresponds to this channel.
        When more than one row of the ifTable is relevant, this is the
        index of the row representing the topmost layer in the
        interface hierarchy.  A value of zero indicates that no
        interface is associated with this channel.
        NOTE: The above description has been modified from RFC 1759
        for clarification."
::= { prtChannelEntry 7 }

prtChannelStatus OBJECT-TYPE
        SYNTAX     PrtSubUnitStatusTC
        MAX-ACCESS read-only
        STATUS     current
        DESCRIPTION
        "The current status of the channel."
::= { prtChannelEntry 8 }

prtChannelInformation OBJECT-TYPE
        SYNTAX     OCTET STRING (SIZE (0..255))
        MAX-ACCESS read-only
        STATUS     current
        DESCRIPTION
        "Auxiliary information to allow a printing application to use
        the channel for data submission to the printer.  An application
        capable of using a specific PrtChannelType should be able to
        use the combined information from the prtChannelInformation and
        other channel and interface group objects to 'bootstrap' its
        use of the channel.  prtChannelInformation is not intended to
        provide a general channel description, nor to provide
        information that is available once the channel is in use.
        The encoding and interpretation of the prtChannelInformation
        object is specific to channel type.  The description of each
        PrtChannelType enum value for which prtChannelInformation is
        defined specifies the appropriate encoding and interpretation,
        including interaction with other objects.  For channel types
        that do not specify a prtChannelInformation value, its value
        shall be null (0 length).
        When a new PrtChannelType enumeration value is registered, its
        accompanying description must specify the encoding and
        interpretation of the prtChannelInformation value for the
        channel type.  prtChannelInformation semantics for an existing
        PrtChannelType may be added or amended in the same manner as
        described in section 2.4.1 for type 2 enumeration values.
        The prtChannelInformation specifies values for a collection of
        channel attributes, represented as text according to the
        following rules:
        1. The prtChannelInformation is not affected by localization.
        2. The prtChannelInformation is a list of entries representing
        the attribute values.  Each entry consists of the following
        items, in order:
        a. A keyword, composed of alphabetic characters (A-Z, a-z)
        represented by their NVT ASCII [RFC854] codes, that
        identifies a channel attribute,
        b. The NVT ASCII code for an Equals Sign (=) (code 61) to
        delimit the keyword,
        c. A data value encoded using rules specific to the
        PrtChannelType to with the prtChannelInformation applies which
        must in no case allow an octet with value 10 (the NVT ASCII
        Line Feed code),
        d. the NVT ASCII code for a Line Feed character (code 10) to
        delimit the data value.
        No other octets shall be present.
        Keywords are case-sensitive.  Conventionally, keywords are
        capitalized (including each word of a multi-word keyword) and
        since they occupy space in the prtChannelInformation, they are
        kept short.
        3. If a channel attribute has multiple values, it is
        represented by multiple entries with the same keyword, each
        specifying one value. Otherwise, there shall be at most one
        entry for each attribute.
        4. By default, entries may appear in any order.  If there are
        ordering constraints for particular entries, these must be
        specified in their definitions.
        5. The prtChannelInformation value by default consists of text
        represented by NVT ASCII graphics character codes.  However,
        other representations may be specified:
        a. In cases where the prtChannelInformation value contains
        information not normally coded in textual form, whatever
        symbolic representation is conventionally used for the
        information should be used for encoding the
        prtChannelInformation value.  (For instance, a binary port value
        might be represented as a decimal number using NVT ASCII
        codes.)  Such encoding must be specified in the definition of
        the value.
        b. The value may contain textual information in a character set
        other than NVT ASCII graphics characters.  (For instance, an
        identifier might consist of ISO 10646 text encoded using the
        UTF-8 encoding scheme.)  Such a character set and its encoding
        must be specified in the definition of the value.
        6. For each PrtChannelType for which prtChannelInformation
        entries are defined, the descriptive text associated with the
        PrtChannelType enumeration value shall specify the following
        information for each entry:
        Title:        Brief description phrase, e.g.: 'Port name',
        'Service Name', etc.
        Keyword:      The keyword value, e.g.: 'Port' or 'Service'
        Syntax:       The encoding of the entry value if it cannot be
        directly represented by NVT ASCII.
        Status:       'Mandatory', 'Optional', or 'Conditionally
        Mandatory'
        Multiplicity: 'Single' or 'Multiple' to indicate whether the
        entry may be present multiple times.
        Description:  Description of the use of the entry, other
        information required to complete the definition
        (e.g.: ordering constraints, interactions between
        entries).
        Applications that interpret prtChannelInformation should ignore
        unrecognized entries, so they are not affected if new entry
        types are added."
::= { prtChannelEntry 9 }

prtInterpreterLangFamily OBJECT-TYPE
        --  NOTE: In RFC 1759, the enumeration values were implicitly
        --  defined by this object.
        SYNTAX     PrtInterpreterLangFamilyTC
        MAX-ACCESS read-only
        STATUS     current
        DESCRIPTION
        "The family name of a Page Description Language (PDL) or
        control language which this interpreter in the printer can
        interpret or emulate.
        NOTE: The above description has been modified from RFC 1759
        for clarification."
::= { prtInterpreterEntry 2 }

prtInterpreterLangLevel OBJECT-TYPE
        SYNTAX     OCTET STRING (SIZE(0..31))
        MAX-ACCESS read-only
        STATUS     current
        DESCRIPTION
        "The level of the language which this interpreter is
        interpreting or emulating.  This might contain a value like
        '5e'for an interpreter which is emulating level 5e of the PCL
        language.  It might contain '2' for an interpreter which is
        emulating level 2 of the PostScript language.  Similarly it
        might contain '2' for an interpreter which is emulating level 2
        of the HPGL language."
::= { prtInterpreterEntry 3 }

prtInterpreterLangVersion OBJECT-TYPE
        SYNTAX     OCTET STRING (SIZE(0..31))
        MAX-ACCESS read-only
        STATUS     current
        DESCRIPTION
        "The date code or version of the language which this
        interpreter is interpreting or emulating."
::= { prtInterpreterEntry 4 }

prtInterpreterDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A string to identify this interpreter in the localization
        specified by prtGeneralCurrentLocalization as opposed to the
        language which is being interpreted.  It is anticipated that
        this string will allow manufacturers to unambiguously identify
        their interpreters."
::= { prtInterpreterEntry 5 }

prtInterpreterVersion OBJECT-TYPE
        SYNTAX     OCTET STRING (SIZE(0..31))
        MAX-ACCESS read-only
        STATUS     current
        DESCRIPTION
        "The date code, version number, or other product specific
        information tied to this interpreter.  This value is associated
        with the interpreter, rather than with the version of the
        language which is being interpreted or emulated."
::= { prtInterpreterEntry 6 }

prtInterpreterDefaultOrientation OBJECT-TYPE
        --  NOTE: In RFC 1759, the enumeration values were implicitly
        --  defined by this object.
        SYNTAX     PrtPrintOrientationTC
        MAX-ACCESS read-write
        STATUS     current
        DESCRIPTION
        "The current orientation default for this interpreter.  This
        value may be overridden for a particular job (e.g., by a
        command in the input data stream)."
::= { prtInterpreterEntry 7 }

prtInterpreterFeedAddressability OBJECT-TYPE
        -- NOTE: In RFC 1759, the range was not defined.
        SYNTAX     Integer32 (-2..2147483647)
        MAX-ACCESS read-only
        STATUS     current
        DESCRIPTION
        "The maximum interpreter addressability in the feed
        direction in 10000 prtMarkerAddressabilityUnits (as specified
        by prtMarkerDefaultIndex) for this interpreter.  The
        value (-1) means other and specifically indicates that the
        sub-unit places no restrictions on this parameter.  The value
        (-2) means unknown.
        NOTE: The above description has been modified from RFC 1759
        for clarification."
::= { prtInterpreterEntry 8 }

prtInterpreterXFeedAddressability OBJECT-TYPE
        -- NOTE: In RFC 1759, the range was not defined.
        SYNTAX     Integer32 (-2..2147483647)
        MAX-ACCESS read-only
        STATUS     current
        DESCRIPTION
        "The maximum interpreter addressability in the cross feed
        direction in 10000 prtMarkerAddressabilityUnits (as specified
        by prtMarkerDefaultIndex) for this interpreter.  The
        value (-1) means other and specifically indicates that the
        sub-unit places no restrictions on this parameter.  The value
        (-2) means unknown.
        NOTE: The above description has been modified from RFC 1759
        for clarification."
::= { prtInterpreterEntry 9 }

prtInterpreterDefaultCharSetIn OBJECT-TYPE
        SYNTAX     IANACharset
        MAX-ACCESS read-write
        STATUS     current
        DESCRIPTION
        "The default coded character set for input octets encountered
        outside a context in which the Page Description Language
        established the interpretation of the octets.  (Input octets are
        presented to the interpreter through a path defined in the
        channel group.)"
::= { prtInterpreterEntry 10 }

prtInterpreterDefaultCharSetOut OBJECT-TYPE
        SYNTAX     IANACharset
        MAX-ACCESS read-write
        STATUS     current
        DESCRIPTION
        "The default character set for data coming from this
        interpreter through the printer's output channel (i.e. the
        'backchannel')."
::= { prtInterpreterEntry 11 }

prtInterpreterTwoWay OBJECT-TYPE
        --  NOTE: In RFC 1759, the enumeration values were implicitly
        --  defined by this object.
        SYNTAX     PrtInterpreterTwoWayTC
        MAX-ACCESS read-only
        STATUS     current
        DESCRIPTION
        "Indicates whether or not this interpreter returns information
        back to the host."
::= { prtInterpreterEntry 12 }

prtConsoleDisplayBufferText OBJECT-TYPE
        -- In RFC 1759, the SYNTAX was OCTET STRING.  This has been changed
        -- to a TC to better support localization of the object.
        SYNTAX     PrtConsoleDescriptionStringTC
        MAX-ACCESS read-write
        STATUS     current
        DESCRIPTION
        "The content of a line in the logical display buffer of
        the operator's console of the printer.  When a write
        operation occurs, normally a critical message, to one of
        the LineText strings, the agent should make that line
        displayable if a physical display is present.  Writing a zero
        length string clears the line.  It is an implementation-
        specific matter as to whether the agent allows a line to be
        overwritten before it has been cleared.  Printer generated
        strings shall be in the localization specified by
        prtConsoleLocalization.Management Application generated strings
        should be localized by the Management Application."
::= { prtConsoleDisplayBufferEntry 2 }

prtConsoleOnTime OBJECT-TYPE
        -- NOTE: In RFC 1759, the range was not defined.
        SYNTAX     Integer32 (0..2147483647)
        MAX-ACCESS read-write
        STATUS     current
        DESCRIPTION
        "This object, in conjunction with prtConsoleOffTime, defines
        the current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero, the
        lamp is on.  If both values are zero the lamp is off.
        NOTE: The above description has been modified from RFC 1759
        for clarification."
::= { prtConsoleLightEntry 2 }

prtConsoleOffTime OBJECT-TYPE
        -- NOTE: In RFC 1759, the range was not defined.
        SYNTAX     Integer32 (0..2147483647)
        MAX-ACCESS read-write
        STATUS     current
        DESCRIPTION
        "This object, in conjunction with prtConsoleOnTime, defines the
        current status of the light.  If both prtConsoleOnTime and
        prtConsoleOffTime are non-zero, the lamp is blinking and the
        values presented define the on time and off time, respectively,
        in milliseconds.  If prtConsoleOnTime is zero and
        prtConsoleOffTime is non-zero, the lamp is off.  If
        prtConsoleOffTime is zero and prtConsoleOnTime is non-zero, the
        lamp is on.  If both values are zero the lamp is off.
        NOTE: The above description has been modified from RFC 1759
        for clarification."
::= { prtConsoleLightEntry 3 }

prtConsoleColor OBJECT-TYPE
        --  NOTE: In RFC 1759, the enumeration values were implicitly
        --  defined by this object.
        SYNTAX     PrtConsoleColorTC
        MAX-ACCESS read-only
        STATUS     current
        DESCRIPTION
        "The color of this light."
::= { prtConsoleLightEntry 4 }

prtConsoleDescription OBJECT-TYPE
        -- In RFC 1759, the SYNTAX was OCTET STRING.  This has been changed
        -- to a TC to better support localization of the object.
        SYNTAX     PrtConsoleDescriptionStringTC
        MAX-ACCESS read-only
        STATUS     current
        DESCRIPTION
        "The vendor description or label of this light in the
        localization specified by prtConsoleLocalization."
::= { prtConsoleLightEntry 5 }

prtAlertSeverityLevel OBJECT-TYPE
        --  NOTE: In RFC 1759, the enumeration values were implicitly
        --  defined by this object.
        SYNTAX     PrtAlertSeverityLevelTC
        MAX-ACCESS read-only
        STATUS     current
        DESCRIPTION
        "The level of severity of this alert table entry.  The printer
        determines the severity level assigned to each entry into the
        table."
::= { prtAlertEntry 2 }

prtAlertTrainingLevel OBJECT-TYPE
        --  NOTE: In RFC 1759, the enumeration values were implicitly
        --  defined by this object.
        SYNTAX     PrtAlertTrainingLevelTC
        MAX-ACCESS read-only
        STATUS     current
        DESCRIPTION
        "See TEXTUAL-CONVENTION PrtAlertTrainingLevelTC.
        NOTE: The above description has been modified from RFC 1759
        for clarification."
::= { prtAlertEntry 3 }

prtAlertGroup OBJECT-TYPE
        --  NOTE: In RFC 1759, the enumeration values were implicitly
        --  defined by this object.
        SYNTAX     PrtAlertGroupTC
        MAX-ACCESS read-only
        STATUS     current
        DESCRIPTION
        "The type of sub-unit within the printer model that this alert
        is related.  Input, output, and markers are examples of printer
        model groups, i.e., examples of types of sub-units.  Wherever
        possible, these enumerations match the sub-identifier that
        identifies the relevant table in the printmib."
::= { prtAlertEntry 4 }

prtAlertGroupIndex OBJECT-TYPE
        -- NOTE: In RFC 1759, the range was not defined.
        SYNTAX     Integer32 (-1..2147483647)
        MAX-ACCESS read-only
        STATUS     current
        DESCRIPTION
        "The low-order index of the row within the table identified
        by prtAlertGroup that represents the sub-unit of the printer
        that caused this alert, or -1 if not applicable.  The
        combination of the prtAlertGroup and the prtAlertGroupIndex
        defines exactly which printer sub-unit caused the alert; for
        example, Input #3, Output#2, and Marker #1.  Every object in
        this MIB is indexed with hrDeviceIndex and optionally, another
        index variable.  If this other index variable is present in the
        table that generated the alert, it will be used as the value
        for this object.  Otherwise, this value shall be -1.
        NOTE: The above description has been modified from RFC 1759
        for clarification."
::= { prtAlertEntry 5 }

prtAlertLocation OBJECT-TYPE
        -- NOTE: In RFC 1759, the range was not defined.
        SYNTAX     Integer32 (-2..2147483647)
        MAX-ACCESS read-only
        STATUS     current
        DESCRIPTION
        "The sub-unit location that is defined by the printer
        manufacturer to further refine the location of this alert
        within the designated sub-unit.  The location is used in
        conjunction with the Group and GroupIndex values; for example,
        there is an alert in Input #2 at location number 7.  The value
        (-2) indicates unknown.
        NOTE: The above description has been modified from RFC 1759
        for clarification."
::= { prtAlertEntry 6 }

prtAlertCode OBJECT-TYPE
        --  NOTE: In RFC 1759, the enumeration values were implicitly
        --  defined by this object.
        SYNTAX     PrtAlertCodeTC
        MAX-ACCESS read-only
        STATUS     current
        DESCRIPTION
        "See associated TEXTUAL-CONVENTION PrtAlertCodeTC.
        NOTE: The above description has been modified from RFC 1759
        for clarification."
::= { prtAlertEntry 7 }

prtAlertDescription OBJECT-TYPE
        -- In RFC 1759, the SYNTAX was OCTET STRING.  This has been changed
        -- to a TC to better support localization of the object.
        SYNTAX     PrtLocalizedDescriptionStringTC
        MAX-ACCESS read-only
        STATUS     current
        DESCRIPTION
        "A description of this alert entry in the localization
        specified by prtGeneralCurrentLocalization.  The description is
        provided by the printer to further elaborate on the enumerated
        alert or provide information in the case where the code is
        classified as 'other' or 'unknown'.  The printer is required to
        return a description string but the string may be a null
        string."
::= { prtAlertEntry 8 }

prtAlertTime OBJECT-TYPE
        SYNTAX     TimeTicks
        MAX-ACCESS read-only
        STATUS     current
        DESCRIPTION
        "The value of sysUpTime at the time that this alert was
        generated."
::= { prtAlertEntry 9 }

gdStatusLineState	OBJECT-TYPE
        SYNTAX			Integer32  ( 0 .. 255  )
        MAX-ACCESS		read-only
        STATUS			current
        DESCRIPTION
        "This describes the line state of the peripheral.
        When non-zero, the peripheral is off-line.  When
        zero the peripheral is on-line."
::=  {  gdStatusEntry  1  }

gdStatusPaperOut	OBJECT-TYPE
        SYNTAX			Integer32
        MAX-ACCESS		read-only
        STATUS			current
        DESCRIPTION
        "This indicates that the peripheral is out of paper.
        off (0),
        paper-out-or-paper-mount (1),
        manual-paper-feed-needed (2)"
::=  {  gdStatusEntry  8  }

gdStatusPaperJam	OBJECT-TYPE
        SYNTAX			Integer32
        MAX-ACCESS		read-only
        STATUS			current
        DESCRIPTION
        "This indicates that the peripheral has a paper jam.
        off (0),
        paper-jam(1)"
::=  {  gdStatusEntry  9  }

gdStatusBusy	OBJECT-TYPE
        SYNTAX			Integer32  ( 0 .. 255  )
        MAX-ACCESS		read-only
        STATUS			current
        DESCRIPTION
        "This indicates that the peripheral is busy processing
        print/plot data."
::=  {  gdStatusEntry  14  }

gdStatusWait	OBJECT-TYPE
        SYNTAX			Integer32  ( 0 .. 255  )
        MAX-ACCESS		read-only
        STATUS			current
        DESCRIPTION
        "This indicates that the peripheral is waiting for print/plot
        data to process."
::=  {  gdStatusEntry  15  }

gdStatusInitialize	OBJECT-TYPE
        SYNTAX			Integer32
        MAX-ACCESS		read-only
        STATUS			current
        DESCRIPTION
        "This indicates that the peripheral is initializing or
        warming up.
        off (0),
        initializing (1),
        warm-up(2)"
::=  {  gdStatusEntry  16  }

gdStatusDoorOpen	OBJECT-TYPE
        SYNTAX			Integer32  ( 0 .. 255  )
        MAX-ACCESS		read-only
        STATUS			current
        DESCRIPTION
        "This indicates that the peripheral cover or door is open."
::=  {  gdStatusEntry  17  }

gdStatusPrinting	OBJECT-TYPE
        SYNTAX			Integer32
        MAX-ACCESS		read-only
        STATUS			current
        DESCRIPTION
        "This indicates that the peripheral is printing or otherwise
        marking or moving paper.
        off (0),
        ordinary-page (1),
        test-fonts-config-or-start-page (2)"
::=  {  gdStatusEntry  18  }

gdStatusPaperOutput	OBJECT-TYPE
        SYNTAX			Integer32
        MAX-ACCESS		read-only
        STATUS			current
        DESCRIPTION
        "This indicates that the peripheral has a paper output problem
        such as the output storage bin being full.
        off (0),
        output-storage-full (1)"
::=  {  gdStatusEntry  19  }

gdStatusDisplay	OBJECT-TYPE
        SYNTAX			DisplayString
        MAX-ACCESS		read-only
        STATUS			current
        DESCRIPTION
        "The string diplayed on the peripheral front panel."
::=  {  generalDeviceStatus  3  }

gdStatusId	OBJECT-TYPE
        SYNTAX			OCTET STRING  ( SIZE ( 0 .. 1024  ) )
        MAX-ACCESS		read-only
        STATUS			current
        DESCRIPTION
        "A formatted string of NVT ASCII
        charactersdescribing this peripheral."
::=  {  generalDeviceStatus  7  }

gdStatusJobTimeout	OBJECT-TYPE
        SYNTAX			Integer32
        MAX-ACCESS		read-write
        STATUS			obsolete
        DESCRIPTION
        "This value represents (in seconds) the maximum time of
        inactivity which must elapse before the print server card
        switches from the current network protocol to another when
        a normal end of job is not detected."
::=  {  generalDeviceStatus  10  }

gdPasswords	OBJECT-TYPE
        SYNTAX			OCTET STRING  ( SIZE ( 0 .. 255  ) )
        MAX-ACCESS		read-write
        STATUS			current
        DESCRIPTION
        "This object is used as a 256 byte NVRAM area for JetAdmin.  It
        is completely managed by JetAdmin.  Initially it is initialized
        to all zeros.  A coldboot will re-initialize to all zeros."
::=  {  generalDeviceStatus  13  }

energy-star OBJECT-TYPE
        SYNTAX  INTEGER
        ACCESS  read-write
        STATUS  optional
        DESCRIPTION
        "Returns or changes the Energy Star sleep value. If the value
        is greater than zero, then the device will go into energy
        saving sleep mode after the print engine has been idle for the
        number of seconds specified by this object. A value of zero
        means Energy Star is disabled and the device will not go to
        sleep based on print engine idle time. The value must be
        non-negative."
::= { settings-system 1 }

sleep-mode OBJECT-TYPE
        SYNTAX  INTEGER {
        eFalse(1),
        eTrue(2)
        }
        ACCESS  read-write
        STATUS  optional
        DESCRIPTION
        "Returns eTrue if the device is in energy saving sleep mode,
        otherwise returns eFalse. Setting SLEEP-MODE to eFalse causes
        the device to wake up, if it is in sleep mode. Setting
        SLEEP-MODE to eTrue causes the device to go into sleep mode."
::= { settings-system 2 }

install-date OBJECT-TYPE
        SYNTAX  DisplayString (SIZE(13))
        ACCESS  read-write
        STATUS  optional
        DESCRIPTION
        "Identifies the date that the device was installed. The format
        of the string is 'YYYYMMDDHHmmZ'. Where:
        YYYY is the year.
        MM is the month (1-12).
        DD is the day (1-31).
        HH is the hour of the day (0-23).
        mm are the minutes (0-59).
        'Z' designates Greenwich Mean Time; if 'Z' not specified,
        value is local time.
        Device POS must specify the conditions for setting this
        object."
::= { status-system 8 }

date-and-time OBJECT-TYPE
        SYNTAX      OCTET STRING
        ACCESS      read-write
        STATUS      optional
        DESCRIPTION "A C structure containing the following fields:    typedef
        struct {
        ubyte yr; /* year: 0 to 99 */
        ubyte mon; /* month: 1 to 12 */
        ubyte day; /* day: 1 to 31 */
        ubyte wday; /* Day of week: 1 to 07 */
        ubyte hr; /* hour: 0 to 23 */
        ubyte min; /* minute: 0 to 59 */
        ubyte sec; /* second: 0 to 59 */
        } date_t;
        where ubyte is an unsigned byte (0-255)."
::= { status-system 17 }

model-number OBJECT-TYPE
        SYNTAX  DisplayString
        ACCESS  read-only
        STATUS  optional
        DESCRIPTION
        "Identifies the device model number as listed in the HP
        corporate price list (e.g. C2121A for DeskJet 500C). The string
        is as specific as possible. Products should note in POS if the
        model number on the CPL changes but the device reports the
        previous model number. If the model number changes based on the
        installed options, the POS should indicate if only the base
        model number is returned, or if the device senses the installed
        options and returns the correct model number. If possible,
        encode the model number in a symbol set (like Roman-8) that
        matches the ASCII character set and limit the characters used
        to ASCII characters."
::= { id 1 }

model-name OBJECT-TYPE
        SYNTAX  DisplayString (SIZE(1..32))
        ACCESS  read-only
        STATUS  optional
        DESCRIPTION
        "Identifies the device model name (e.g. ''DeskJet 1200C''). The
        string is as specific as possible. Capitalization and spacing
        should match family naming conventions. Products should note in
        POS if the model name on the HP corporate price list changes
        but the device reports the previous device name. If the model
        name changes based on the installed options, the POS should
        indicate if only the base model name is returned, or if the
        device senses the installed options and returns the correct
        model name. If possible, encode the model name in a symbol set
        (like Roman-8) that matches the ASCII character set and limit
        the characters used to ASCII characters."
::= { id 2 }

serial-number OBJECT-TYPE
        SYNTAX  DisplayString (SIZE(0..10))
        ACCESS  read-only
        STATUS  optional
        DESCRIPTION
        "Identifies the serial number for the device. If the
        SERIAL-NUMBER object is set by the user, then setting the
        object does not need to be protected. If the SERIAL-NUMBER
        object is set at the factory, then the SERVICE-PASSWORD object
        must be set correctly before the SERIAL-NUMBER object is
        writable. If this is a writable object, the POS should indicate
        the maximum supported string length. If possible, encode the
        serial number in a symbol set (like Roman-8) that matches the
        ASCII character set and limit the characters used to ASCII
        characters."
::= { id 3 }

fw-rom-datecode OBJECT-TYPE
        SYNTAX  DisplayString
        ACCESS  read-only
        STATUS  optional
        DESCRIPTION
        "Identifies the base system firmware date code. The date code
        will be encoded in the yyyymmdd format. There may be several
        versions of the base system firmware. The date code associated
        with the version of the base system firmware that is being used
        is reported. There may be other date code objects for other
        specific modules such as fonts, localization modules, etc.;
        these other datecode objects are device specific."
::= { id 5 }

fw-rom-revision OBJECT-TYPE
        SYNTAX  DisplayString
        ACCESS  read-only
        STATUS  optional
        DESCRIPTION
        "This identifies the system code firmware ROM revision code. The
        format for a revision is major_revision.minor_revision. There
        may be other ROM revision code objects for other specific ROMs
        such as font ROMs, localization ROMs, etc; these other ROM
        revision code objects are device specific."
::= { id 6 }

device-location OBJECT-TYPE
        SYNTAX  DisplayString
        ACCESS  read-write
        STATUS  optional
        DESCRIPTION
        "User defined device location. The POS should indicate the
        maximum supported string length. If the user entered string is
        too long, the device will store as much as possible and will
        return the <OKNearestLegal ValueSubstituted>.Additional information:
        The maximum supported string length is 16
        characters.  If the user entered string is too long,
        the device will store the first 16 characters and will
        return the <noError> status."
::= { id 11 }

asset-number OBJECT-TYPE
        SYNTAX  DisplayString
        ACCESS  read-write
        STATUS  optional
        DESCRIPTION
        "User defined asset number. The POS should indicate the maximum
        supported string length. If the user entered string is too
        long, the device will store as much as possible and will return
        the <OKNearestLegal ValueSubstituted>.Additional information:
        The maximum supported string length is 8
        characters.  If the user entered string is too long,
        the device will store the first 8 characters and will
        return the <noError> status."
::= { id 12 }

print-internal-page OBJECT-TYPE
        SYNTAX  INTEGER {
        eNotPrintingAnInternalPage(1),
        ePrintingAnUnknownInternalPage(2),
        eDeviceDemoPage1ConfigurationPage(3),
        eDeviceDemoPage2(4),
        eDeviceDemoPage5ErrorLog(7),
        eDeviceDemoPage6FileSystemDirectoryListing(8),
        eDeviceDemoPage7MenuMap(9),
        ePrintUsagePage(100),
        eSuppliesPage(101),
        eDevicePaperPathTest(254),
        eDevicePageRegistrationPage(255),
        ePrintQualityPages(256),
        ePCLFontList1(350),
        ePSFontList(450)
        }
        ACCESS  read-write
        STATUS  optional
        DESCRIPTION
        "Writing this object to a value other than
        eNotPrintingAnInternalPage causes the device to attempt to
        print an internally generated page. Reading this object
        provides an indication what internally generated page is
        currently being printed, if any. The actual page is device
        specific. Some devices may support continuously printing an
        internally generated page. Setting this object to
        eNotPrintingAnInternalPage terminates continuously printing
        internally generated pages. An internally generated page may
        not be allowed to be printed at any arbitrary time; under what
        conditions it will succeed or fail is device specific. If the
        device supports the requested page, but can not start printing
        the page when requested, the device will respond with
        <genErr>. RECOMMENDATION: If the
        device is ready (i.e. the NOT-READY-PRINTER object does not
        contain any items, except maybe being off-line) and is idle
        (i.e. the NOT-IDLE object does not contain any items), this
        request should always succeed. This provides a mechanism for
        driver writers to always determine if the action will succeed
        or not."
::= { test 2 }

error1-time-stamp OBJECT-TYPE
        SYNTAX  INTEGER
        ACCESS  read-only
        STATUS  optional
        DESCRIPTION
        "Contains some sort of time stamp indicating when error 1
        occurred. Example time stamps include the actual time the error
        occurred (in seconds since Jan. 1, 1970), and the total engine
        page count. The device POS documents the meaning of the time
        stamp."
::= { error1 1 }

error1-code OBJECT-TYPE
        SYNTAX  INTEGER
        ACCESS  read-only
        STATUS  optional
        DESCRIPTION
        "Contains a device specific error code. Each device POS should
        list what errors are logged to the error log and the meaning of
        each supported error code value."
::= { error1 2 }

error1-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error1 3 }

error2-time-stamp OBJECT-TYPE
        SYNTAX  INTEGER
        ACCESS  read-only
        STATUS  optional
        DESCRIPTION
        "Contains some sort of time stamp indicating when error 2
        occurred. Example time stamps include the actual time the error
        occurred (in seconds since Jan. 1, 1970), and the total engine
        page count. The device POS documents the meaning of the time
        stamp."
::= { error2 1 }

error2-code OBJECT-TYPE
        SYNTAX  INTEGER
        ACCESS  read-only
        STATUS  optional
        DESCRIPTION
        "Contains a device specific error code. Each device POS should
        list what errors are logged to the error log and the meaning of
        each supported error code value."
::= { error2 2 }

error2-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error2 3 }

error3-time-stamp OBJECT-TYPE
        SYNTAX  INTEGER
        ACCESS  read-only
        STATUS  optional
        DESCRIPTION
        "Contains some sort of time stamp indicating when error 3
        occurred. Example time stamps include the actual time the error
        occurred (in seconds since Jan. 1, 1970), and the total engine
        page count. The device POS documents the meaning of the time
        stamp."
::= { error3 1 }

error3-code OBJECT-TYPE
        SYNTAX  INTEGER
        ACCESS  read-only
        STATUS  optional
        DESCRIPTION
        "Contains a device specific error code. Each device POS should
        list what errors are logged to the error log and the meaning of
        each supported error code value."
::= { error3 2 }

error3-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error3 3 }

error4-time-stamp OBJECT-TYPE
        SYNTAX  INTEGER
        ACCESS  read-only
        STATUS  optional
        DESCRIPTION
        "Contains some sort of time stamp indicating when error 4
        occurred. Example time stamps include the actual time the error
        occurred (in seconds since Jan. 1, 1970), and the total engine
        page count. The device POS documents the meaning of the time
        stamp."
::= { error4 1 }

error4-code OBJECT-TYPE
        SYNTAX  INTEGER
        ACCESS  read-only
        STATUS  optional
        DESCRIPTION
        "Contains a device specific error code. Each device POS should
        list what errors are logged to the error log and the meaning of
        each supported error code value."
::= { error4 2 }

error4-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error4 3 }

error5-time-stamp OBJECT-TYPE
        SYNTAX  INTEGER
        ACCESS  read-only
        STATUS  optional
        DESCRIPTION
        "Contains some sort of time stamp indicating when error 5
        occurred. Example time stamps include the actual time the error
        occurred (in seconds since Jan. 1, 1970), and the total engine
        page count. The device POS documents the meaning of the time
        stamp."
::= { error5 1 }

error5-code OBJECT-TYPE
        SYNTAX  INTEGER
        ACCESS  read-only
        STATUS  optional
        DESCRIPTION
        "Contains a device specific error code. Each device POS should
        list what errors are logged to the error log and the meaning of
        each supported error code value."
::= { error5 2 }

error5-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error5 3 }

error6-time-stamp OBJECT-TYPE
        SYNTAX  INTEGER
        ACCESS  read-only
        STATUS  optional
        DESCRIPTION
        "Contains some sort of time stamp indicating when error 6
        occurred. Example time stamps include the actual time the error
        occurred (in seconds since Jan. 1, 1970), and the total engine
        page count. The device POS documents the meaning of the time
        stamp."
::= { error6 1 }

error6-code OBJECT-TYPE
        SYNTAX  INTEGER
        ACCESS  read-only
        STATUS  optional
        DESCRIPTION
        "Contains a device specific error code. Each device POS should
        list what errors are logged to the error log and the meaning of
        each supported error code value."
::= { error6 2 }

error6-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error6 3 }

error7-time-stamp OBJECT-TYPE
        SYNTAX  INTEGER
        ACCESS  read-only
        STATUS  optional
        DESCRIPTION
        "Contains some sort of time stamp indicating when error 7
        occurred. Example time stamps include the actual time the error
        occurred (in seconds since Jan. 1, 1970), and the total engine
        page count. The device POS documents the meaning of the time
        stamp."
::= { error7 1 }

error7-code OBJECT-TYPE
        SYNTAX  INTEGER
        ACCESS  read-only
        STATUS  optional
        DESCRIPTION
        "Contains a device specific error code. Each device POS should
        list what errors are logged to the error log and the meaning of
        each supported error code value."
::= { error7 2 }

error7-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error7 3 }

error8-time-stamp OBJECT-TYPE
        SYNTAX  INTEGER
        ACCESS  read-only
        STATUS  optional
        DESCRIPTION
        "Contains some sort of time stamp indicating when error 8
        occurred. Example time stamps include the actual time the error
        occurred (in seconds since Jan. 1, 1970), and the total engine
        page count. The device POS documents the meaning of the time
        stamp."
::= { error8 1 }

error8-code OBJECT-TYPE
        SYNTAX  INTEGER
        ACCESS  read-only
        STATUS  optional
        DESCRIPTION
        "Contains a device specific error code. Each device POS should
        list what errors are logged to the error log and the meaning of
        each supported error code value."
::= { error8 2 }

error8-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error8 3 }

error9-time-stamp OBJECT-TYPE
        SYNTAX  INTEGER
        ACCESS  read-only
        STATUS  optional
        DESCRIPTION
        "Contains some sort of time stamp indicating when error 9
        occurred. Example time stamps include the actual time the error
        occurred (in seconds since Jan. 1, 1970), and the total engine
        page count. The device POS documents the meaning of the time
        stamp."
::= { error9 1 }

error9-code OBJECT-TYPE
        SYNTAX  INTEGER
        ACCESS  read-only
        STATUS  optional
        DESCRIPTION
        "Contains a device specific error code. Each device POS should
        list what errors are logged to the error log and the meaning of
        each supported error code value."
::= { error9 2 }

error9-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error9 3 }

error10-time-stamp OBJECT-TYPE
        SYNTAX  INTEGER
        ACCESS  read-only
        STATUS  optional
        DESCRIPTION
        "Contains some sort of time stamp indicating when error 10
        occurred. Example time stamps include the actual time the error
        occurred (in seconds since Jan. 1, 1970), and the total engine
        page count. The device POS documents the meaning of the time
        stamp."
::= { error10 1 }

error10-code OBJECT-TYPE
        SYNTAX  INTEGER
        ACCESS  read-only
        STATUS  optional
        DESCRIPTION
        "Contains a device specific error code. Each device POS should
        list what errors are logged to the error log and the meaning of
        each supported error code value."
::= { error10 2 }

error10-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error10 3 }

error11-time-stamp OBJECT-TYPE
        SYNTAX  INTEGER
        ACCESS  read-only
        STATUS  optional
        DESCRIPTION
        "Contains some sort of time stamp indicating when error 11
        occurred. Example time stamps include the actual time the error
        occurred (in seconds since Jan. 1, 1970), and the total engine
        page count. The device POS documents the meaning of the time
        stamp."
::= { error11 1 }

error11-code OBJECT-TYPE
        SYNTAX  INTEGER
        ACCESS  read-only
        STATUS  optional
        DESCRIPTION
        "Contains a device specific error code. Each device POS should
        list what errors are logged to the error log and the meaning of
        each supported error code value."
::= { error11 2 }

error11-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error11 3 }

error12-time-stamp OBJECT-TYPE
        SYNTAX  INTEGER
        ACCESS  read-only
        STATUS  optional
        DESCRIPTION
        "Contains some sort of time stamp indicating when error 12
        occurred. Example time stamps include the actual time the error
        occurred (in seconds since Jan. 1, 1970), and the total engine
        page count. The device POS documents the meaning of the time
        stamp."
::= { error12 1 }

error12-code OBJECT-TYPE
        SYNTAX  INTEGER
        ACCESS  read-only
        STATUS  optional
        DESCRIPTION
        "Contains a device specific error code. Each device POS should
        list what errors are logged to the error log and the meaning of
        each supported error code value."
::= { error12 2 }

error12-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error12 3 }

error13-time-stamp OBJECT-TYPE
        SYNTAX  INTEGER
        ACCESS  read-only
        STATUS  optional
        DESCRIPTION
        "Contains some sort of time stamp indicating when error 13
        occurred. Example time stamps include the actual time the error
        occurred (in seconds since Jan. 1, 1970), and the total engine
        page count. The device POS documents the meaning of the time
        stamp."
::= { error13 1 }

error13-code OBJECT-TYPE
        SYNTAX  INTEGER
        ACCESS  read-only
        STATUS  optional
        DESCRIPTION
        "Contains a device specific error code. Each device POS should
        list what errors are logged to the error log and the meaning of
        each supported error code value."
::= { error13 2 }

error13-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error13 3 }

error14-time-stamp OBJECT-TYPE
        SYNTAX  INTEGER
        ACCESS  read-only
        STATUS  optional
        DESCRIPTION
        "Contains some sort of time stamp indicating when error 14
        occurred. Example time stamps include the actual time the error
        occurred (in seconds since Jan. 1, 1970), and the total engine
        page count. The device POS documents the meaning of the time
        stamp."
::= { error14 1 }

error14-code OBJECT-TYPE
        SYNTAX  INTEGER
        ACCESS  read-only
        STATUS  optional
        DESCRIPTION
        "Contains a device specific error code. Each device POS should
        list what errors are logged to the error log and the meaning of
        each supported error code value."
::= { error14 2 }

error14-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error14 3 }

error15-time-stamp OBJECT-TYPE
        SYNTAX  INTEGER
        ACCESS  read-only
        STATUS  optional
        DESCRIPTION
        "Contains some sort of time stamp indicating when error 15
        occurred. Example time stamps include the actual time the error
        occurred (in seconds since Jan. 1, 1970), and the total engine
        page count. The device POS documents the meaning of the time
        stamp."
::= { error15 1 }

error15-code OBJECT-TYPE
        SYNTAX  INTEGER
        ACCESS  read-only
        STATUS  optional
        DESCRIPTION
        "Contains a device specific error code. Each device POS should
        list what errors are logged to the error log and the meaning of
        each supported error code value."
::= { error15 2 }

error15-date-time OBJECT-TYPE
        SYNTAX      OCTET STRING
        ACCESS      read-only
        STATUS      optional
        DESCRIPTION "This item contains the date and the time at which an error
        occurred. The values returned will be in hexadecimal. If the
        date is 2004-Jul-13 and the time is 03:15 a.m., we get 04 07 0d
        03 0f where,
        04 (hex) - corresponds to the year 2004.
        07 (hex) - corresponds to month, 07
        0d (hex) - corresponds to date, 13
        03 (hex) - corresponds to hour, 3 a.m.
        0f (hex) - corresponds to min, 15."
::= { error15 3 }

printed-media-simplex-count OBJECT-TYPE
        SYNTAX  INTEGER(0..930576247)
        ACCESS  read-only
        STATUS  optional
        DESCRIPTION
        "Total number of simplex pages printed in this media size.
        Additional information:
        The 5 usage (simplex/duplex count, simplex/duplex click
        charge and paper size total) objects described here and
        below detail the usage for the printer for each paper
        size defined in the PCL Implementor's Guide and in the
        Media Size Table in the hpmib.txt.  The OID binding is
        based on the click attribute and paper size.
        For example:
        The format for the OID is as follows:
        3.4.1.5.x.y
        <-----> | |
        |    |  \
        /     |  paper size
        /       \
        PRINTER-CLICK_TOTALS ROOT   \
        OID                      click attribute 1..5
        x values are 1..5:
        1) simplex count
        2) simplex click charge
        3) duplex count
        4) duplex click charge
        5) printer or scanner paper size total (i.e. depends if the
        root OID is referrring to the printer or scanner).
        y : paper size as defined in the Media Size Table in the
        hpmib.txt "
::= { printed-media-usage 1 }

printed-media-duplex-count OBJECT-TYPE
        SYNTAX  INTEGER(0..930576247)
        ACCESS  read-only
        STATUS  optional
        DESCRIPTION
        "Total number of duplex pages printed in this media size."
::= { printed-media-usage 3 }

printed-media-color-simplex-count OBJECT-TYPE
        SYNTAX  INTEGER
        ACCESS  read-only
        STATUS  optional
        DESCRIPTION
        "Total number of color simplex pages printed in this media
        size."
::= { printed-media-color-usage 1 }

printed-media-color-duplex-count OBJECT-TYPE
        SYNTAX  INTEGER
        ACCESS  read-only
        STATUS  optional
        DESCRIPTION
        "Total number of color duplex pages printed in this media size."
::= { printed-media-color-usage 3 }

scanner-accessory-adf-sheet-count OBJECT-TYPE
        SYNTAX      INTEGER(0..2147483647)
        ACCESS      read-only
        STATUS      optional
        DESCRIPTION "Total number of sheets that have been fed through the Automatic
        Document Feed (ADF) accessory.
        Additional information:
        The Automatic Document Feed (ADF) count is
        incremented each time a sheet feeds through the
        ADF.
        The value will be updated at the end of every
        scan job. "
::= { settings-scanner 20 }

scanner-accessory-flatbed-scan-count OBJECT-TYPE
        SYNTAX      INTEGER(0..2147483647)
        ACCESS      read-only
        STATUS      optional
        DESCRIPTION "Total number of scans performed by a flatbed scanner
        accessory.
        Additional information:
        The count is only incremented when a sheet is
        scanned on the FLATBED.
        The return value of this object will reset
        to the lower multiple of 10 at a power cycle.
        The value will be updated at the end of every
        scan job. "
::= { settings-scanner 21 }

scanner-accessory-copy-job-scan-count OBJECT-TYPE
        SYNTAX      INTEGER
        ACCESS      read-only
        STATUS      optional
        DESCRIPTION "This relates to the number of pages scanned for copying. This
        item is incremented by 2 for each sheet scanned through the ADF
        in 2-sided scan mode, and it is incremented by 1 for flatbed
        scans. Scanning for testing and calibration purposes are NOT TO
        BE INCLUDED in this count.
        Additional information:
        The value will be updated at the end of every
        scan job. "
::= { settings-scanner 61 }

scanner-accessory-send-job-scan-count OBJECT-TYPE
        SYNTAX      INTEGER
        ACCESS      read-only
        STATUS      optional
        DESCRIPTION "This relates to the number of pages scanned for fax/send. This
        item is incremented by 2 for each sheet scanned through the ADF
        in 2-sided scan mode, and it is incremented by 1 for flatbed
        scans. Scanning for testing and calibration purposes are NOT TO
        BE INCLUDED in this count.
        Additional information:
        The value will be updated at the end of every
        scan job. "
::= { settings-scanner 62 }

scanner-accessory-total-copy-pages-printed OBJECT-TYPE
        SYNTAX      INTEGER
        ACCESS      read-only
        STATUS      optional
        DESCRIPTION "This relates to the number of copy pages printed on a device.
        The output sheet that is duplexed (made 2- sided) should be
        counted as 2 pages."
::= { settings-scanner 63 }

scan-to-folder-count OBJECT-TYPE
        SYNTAX      INTEGER(0..9999999)
        ACCESS      read-only
        STATUS      optional
        DESCRIPTION "The number of scan-to-folder scan jobs.
        Additional information:
        The number of scan-to-folder scan jobs."
::= { settings-scanner 89 }

fax-job-scan-count OBJECT-TYPE
        SYNTAX      INTEGER(0..9999999)
        ACCESS      read-only
        STATUS      optional
        DESCRIPTION "The number of fax scan jobs.
        Additional information:
        The number of fax scan jobs."
::= { settings-scanner 90 }

pcl-total-page-count OBJECT-TYPE
        SYNTAX  INTEGER
        ACCESS  read-only
        STATUS  optional
        DESCRIPTION
        "Total number of PCL pages printed by the device.
        Additional information:
        The page count is incremented when a sheet of media is pulled from an input
        tray. A duplex printed sheet will cause this counter to be incremented by
        two."
::= { pdl-pcl 5 }

postscript-total-page-count OBJECT-TYPE
        SYNTAX  INTEGER
        ACCESS  read-only
        STATUS  optional
        DESCRIPTION
        "Total number of PostScript pages printed by the device."
::= { pdl-postscript 5 }

afax-send-page-count OBJECT-TYPE
        SYNTAX      INTEGER
        ACCESS      read-write
        STATUS      optional
        DESCRIPTION "Keeps the total number of pages sent successfully via the
        analog fax modem. This count would be synchronised with the
        number of fax jobs sent successfully. The <<hidden>> must
        be set correctly to write this object."
::= { status-fax-proc-sub 11 }

afax-recv-page-count OBJECT-TYPE
        SYNTAX      INTEGER
        ACCESS      read-write
        STATUS      optional
        DESCRIPTION "Keeps the total number of pages received successfully via the
        analog fax modem. This count would be synchronised with the
        number of fax jobs received successfully. The <<hidden>>
        must be set correctly to write this object."
::= { status-fax-proc-sub 12 }

total-color-page-count OBJECT-TYPE
        SYNTAX  INTEGER
        ACCESS  read-only
        STATUS  optional
        DESCRIPTION
        "Total number of color pages printed by the device.
        Additional information:
        Any page with one or more color pixels is counted as a color page. Pages that only
        contain black marks are not counted by this object.
        A duplexed sheet of media will cause the counter to be incremented by two."
::= { status-prt-eng 7 }

duplex-page-count OBJECT-TYPE
        SYNTAX  INTEGER
        ACCESS  read-only
        STATUS  optional
        DESCRIPTION
        "Total number of sheets of media that have been duplex printed.
        A sheet is counted if it travels through the duplex page path,
        regardless of whether or not marks are made on the page. The
        POS will indicate if the value is kept in NVRAM."
::= { status-prt-eng 22 }

consumable-status-cartridge-model OBJECT-TYPE
        SYNTAX  DisplayString (SIZE(0..24))
        ACCESS  read-only
        STATUS  optional
        DESCRIPTION
        "This object is used to read the cartridge model number
        associated with this consumable.
        Additional information:
        This object will only exist for Authentic HP consumables.
        If the cartridge is deemed to be NonHP, then this object
        will not exist."
::= { consumable-status 1 }

consumable-status-manufacturing-date OBJECT-TYPE
        SYNTAX  DisplayString (SIZE(0..24))
        ACCESS  read-only
        STATUS  optional
        DESCRIPTION
        "This object is used to report the date on which this consumable
        was manufactured. The format of the string is 'YYYYMMDD', where
        YYYY is the year, MM is the month (1-12), and DD is the day
        (1-31).
        Additional information:
        This object will only exist for Authentic HP consumables.
        If the cartridge is deemed to be NonHP, then this object
        will not exist."
::= { consumable-status 2 }

consumable-status-serial-number OBJECT-TYPE
        SYNTAX  DisplayString (SIZE(0..24))
        ACCESS  read-only
        STATUS  optional
        DESCRIPTION
        "This object is used to report the serial number for this
        consumable.
        Additional information:
        This object will only exist for Authentic HP consumables.
        If the cartridge is deemed to be NonHP, then this object
        will not exist."
::= { consumable-status 3 }

consumable-status-first-install-date OBJECT-TYPE
        SYNTAX  DisplayString (SIZE(0..24))
        ACCESS  read-only
        STATUS  optional
        DESCRIPTION
        "This object is used to report the date on which this consumable
        was first installed. The format of the string is 'YYYYMMDD'.
        Where:
        YYYY is the year.
        MM is the month (1-12).
        DD is the day (1-31).
        The device POS needs to indicate what will be written in the
        event the printer does not have a real time clock.
        Additional information:
        This object will only exist for Authentic HP consumables.
        If the cartridge is deemed to be NonHP, then this object
        will not exist. For printers without internal clocks, the
        date will always be 20000101."
::= { consumable-status 8 }

npSysModelNumber	OBJECT-TYPE
        SYNTAX			OCTET STRING  ( SIZE ( 6  ) )
        MAX-ACCESS		read-only
        STATUS			current
        DESCRIPTION
        "The HP model number of the device."
::=  {  npSys  10  }

npSysCardServices1	OBJECT-TYPE
        SYNTAX			Integer32
        MAX-ACCESS		read-only
        STATUS			current
        DESCRIPTION
        "This object is a bitmap showing what services are available
        on the card.
        Bit  0 - IPX/SPX/NCP protocol stack
        Bit  1 - IP/TCP protocol stack
        Bit  2 - LLC/DLC protocol stack
        Bit  3 - Ethertalk protocol stack
        Bit  4 - IPv6 protocol stack
        Bit  5 - IPSec protocol stack
        Bits  6 - 11 Reserved
        Bit 12 - LPD print services
        Bit 13 - FTP print services
        Bit 14 - Port 9100 print services
        Bit 15 - IPP print services
        Bits 16 - 23 Reserved
        Bit 24 - Queue Server Bindery
        Bit 25 - Queue Server NDS
        Bit 26 - Remote Printer
        Bit 27 - SPX Direct Mode
        Bit 28 - DLC Print Services
        Bit 29 - EtherTalk Print Services
        Bits 30 - 31 Reserved"
::=  {  npSys  16  }

npSysCardServices2	OBJECT-TYPE
        SYNTAX			Integer32
        MAX-ACCESS		read-only
        STATUS			current
        DESCRIPTION
        "This object is a bitmap showing what services are available
        on the card.
        Bit  0 - XIP2
        Bit  1 - PML Get/Set
        Bit  2 - PML Traps
        Bit  3 - Scan to Web Browser
        Bit  4 - Scan to Email
        Bit  5 - MFP Scan Support
        Bits  6 - 11 Reserved
        Bit 12 - Telnet API
        Bit 13 - Web API
        Bit 14 - SNMP V2
        Bit 15 - SNMP Traps
        Bit 16 - Download
        Bit 17 - TFTP
        Bit 18 - RCFG
        Bit 19 - SLP
        Bit 20 - Syslog
        Bit 21 - DHCP
        Bit 22 - BOOTP
        Bit 23 - RARP
        Bit 24 - SNMP V3
        Bit 25 - SSL Functionality
        Bit 26 - Auto IP
        Bit 27 - SNMP V3 SHA-1 & AES-128 support.
        Bits 28 - 31 Reserved"
::=  {  npSys  17  }

npSysCardServices3	OBJECT-TYPE
        SYNTAX			Integer32
        MAX-ACCESS		read-only
        STATUS			current
        DESCRIPTION
        "This object is a bitmap showing what services are available
        on the card.
        Bit  0 - 100T
        Bit  1 - Token Ring 802.5
        Bit  2 - 802.11b
        Bit  3 - 80211.a
        Bit  4 - Bluetooth
        Bits 5 - 11 Reserved
        Bit  12 -  EIO. For embedded Jetdirect this bit will be 1.
        Bit  13 - LIO
        Bit  14 - USB
        Bit  15 - Firewire
        Bit  16 - TCP Download
        Bits 17 - 31 Reserved"
::=  {  npSys  22  }

npSysFactoryMacAddress	OBJECT-TYPE
        SYNTAX			OCTET STRING
        MAX-ACCESS		read-only
        STATUS			current
        DESCRIPTION
        "Factory assigned hardware (MAC) address"
::=  {  npSys  23  }

npCfgSource	OBJECT-TYPE
        SYNTAX			INTEGER  { manual-one ( 1 ) , bootp-two ( 2 ) , manual-three ( 3 ) , bootp-four ( 4 ) , dhcp ( 5 ) , not-configured ( 6 ) , default-config ( 7 ) , rarp ( 8 ) , read-only ( 9 ) , auto-ip ( 10 ) }
        MAX-ACCESS		read-write
        STATUS			current
        DESCRIPTION
        "This object indicates how the device obtained its IP configuration."
::=  {  npCfg  1  }

npCfgYiaddr	OBJECT-TYPE
        SYNTAX			IpAddress
        MAX-ACCESS		read-write
        STATUS			current
        DESCRIPTION
        "The IP address assigned to the card from the BOOTP reply
        yiaddr field."
::=  {  npCfg  2  }

npCfgSiaddr	OBJECT-TYPE
        SYNTAX			IpAddress
        MAX-ACCESS		read-only
        STATUS			current
        DESCRIPTION
        "The IP address of the TFTP server from the BOOTP reply
        siaddr field."
::=  {  npCfg  3  }

npCfgSubnetMask	OBJECT-TYPE
        SYNTAX			IpAddress
        MAX-ACCESS		read-write
        STATUS			current
        DESCRIPTION
        "The subnet mask associated with the IP address of this card."
::=  {  npCfg  12  }

npCfgDefaultGateway	OBJECT-TYPE
        SYNTAX			IpAddress
        MAX-ACCESS		read-write
        STATUS			current
        DESCRIPTION
        "This variable contains the IP address of the default router for this
        card."
::=  {  npCfg  13  }

npCfgDomainName	OBJECT-TYPE
        SYNTAX			OCTET STRING  ( SIZE ( 0 .. 255  ) )
        MAX-ACCESS		read-write
        STATUS			current
        DESCRIPTION
        "The print server domain name."
::=  {  npCfg  16  }

npCfgIPP	OBJECT-TYPE
        SYNTAX			Integer32
        MAX-ACCESS		read-write
        STATUS			current
        DESCRIPTION
        "Below are the different values accepted by this OID.
        0 - Disable IPP and IPP-S
        1 - Enable IPP and IPP-S
        2 - Enable IPP-S only
        3 - Enable IPP only
        "
::=  {  npCfg  18  }

npCfgDNSNameServerId	OBJECT-TYPE
        SYNTAX			IpAddress
        MAX-ACCESS		read-write
        STATUS			current
        DESCRIPTION
        "IP address of Primary DNS name-server."
::=  {  npCfg  21  }

npCfgWINSNameServerIdPri	OBJECT-TYPE
        SYNTAX			IpAddress
        MAX-ACCESS		read-write
        STATUS			current
        DESCRIPTION
        "Primary name server for NetBIOS over TCP/IP."
::=  {  npCfg  22  }

npCfgWINSNameServerIdSec	OBJECT-TYPE
        SYNTAX			IpAddress
        MAX-ACCESS		read-write
        STATUS			current
        DESCRIPTION
        "Secondary name server for NetBIOS over TCP/IP."
::=  {  npCfg  23  }

npCfgPasswd1Verify	OBJECT-TYPE
        SYNTAX			OCTET STRING  ( SIZE ( 0 .. 16  ) )
        MAX-ACCESS		read-write
        STATUS			current
        DESCRIPTION
        "Compares string value to passwd1 and returns OK if match,
        GENERAL ERROR if doesn't match."
::=  {  npCfg  28  }

npCfgPasswd1	OBJECT-TYPE
        SYNTAX			DisplayString
        MAX-ACCESS		read-write
        STATUS			current
        DESCRIPTION
        "Password for root or administrator. Get request returns
        either 'SET' or 'NOT_SET'."
::=  {  npCfg  29  }

npCfgLinkType	OBJECT-TYPE
        SYNTAX			INTEGER  { autoNegotiate ( 1 ) , full10T ( 2 ) , half10T ( 3 ) , full100T ( 4 ) , half100T ( 5 ) , auto100T ( 6 ) , full1000T ( 7 ) }
        MAX-ACCESS		read-write
        STATUS			current
        DESCRIPTION
        "Network link speed and communication mode."
::=  {  npCfg  35  }

npCfgSnmpDefaultReadCmnty	OBJECT-TYPE
        SYNTAX			Integer32  ( 0 .. 1  )
        MAX-ACCESS		read-write
        STATUS			current
        DESCRIPTION
        "Controls Default Read Community Name access.
        (0) = Disabled, i.e., default get community names FAIL to access target.
        (1) = Enabled,  i.e., default get community names SUCCEED to access target."
::=  {  npCfg  40  }

npCfgBonjourDomainName	OBJECT-TYPE
        SYNTAX			OCTET STRING  ( SIZE ( 0 .. 255  ) )
        MAX-ACCESS		read-only
        STATUS			current
        DESCRIPTION
        "The name used as the 'target name' in the DNS SRV records by
        Multicast Domain Name System (Bonjour)."
::=  {  npCfg  46  }

npCfgDNSNameServerIdSecondary	OBJECT-TYPE
        SYNTAX			IpAddress
        MAX-ACCESS		read-write
        STATUS			current
        DESCRIPTION
        "IP address of Secondary DNS name-server."
::=  {  npCfg  47  }

npCfgIPv6DomainName	OBJECT-TYPE
        SYNTAX			OCTET STRING
        MAX-ACCESS		read-write
        STATUS			current
        DESCRIPTION
        "IPv6 Domain Name."
::=  {  npCfg  49  }

npCfgIPv6ConfigState	OBJECT-TYPE
        SYNTAX			INTEGER  { ipv6-going-down ( 0 ) , ipv6-is-up ( 1 ) }
        MAX-ACCESS		read-only
        STATUS			current
        DESCRIPTION
        "IPv6 stack status event; IPv6 enabled/disabled."
::=  {  npCfg  50  }

npCfgIPAddrIndex	OBJECT-TYPE
        SYNTAX			Integer32  ( -2147483648 .. 2147483647  )
        MAX-ACCESS		read-only
        STATUS			current
::=  {  npCfgIPAddrEntry  1  }

npCfgIPAddrType	OBJECT-TYPE
        SYNTAX			InetAddressType  { unknown ( 0 ) , ipv4 ( 1 ) , ipv6 ( 2 ) , ipv4z ( 3 ) , ipv6z ( 4 ) , dns ( 16 ) }
        MAX-ACCESS		read-only
        STATUS			current
        DESCRIPTION
        "The address type of npCfgIPAddress.
        unknown(0)	An unknown address type. This value MUST
        be used if the value of the corresponding
        InetAddress object is a zero-length string.
        It may also be used to indicate an IP address
        which is not in one of the formats defined below.
        ipv4(1)		An IPv4 address as defined by the
        InetAddressIPv4 textual convention.
        ipv6(2)		A global IPv6 address as defined by the
        InetAddressIPv6 textual convention.
        ipv4z(3)	A non-global IPv4 address including a zone
        index as defined by the InetAddressIPv4z
        textual convention.
        ipv6z(4)	A non-global IPv6 address including a zone
        index as defined by the InetAddressIPv6z
        textual convention.
        dns(16)		A DNS domain name as defined by the
        InetAddressDNS textual convention.
        For more details please refer RFC 3291, RFC 4001.
        "
::=  {  npCfgIPAddrEntry  2  }

npCfgIPAddress	OBJECT-TYPE
        SYNTAX			InetAddress  ( SIZE ( 0 .. 255  ) )
        MAX-ACCESS		read-only
        STATUS			current
        DESCRIPTION
        "The IP address to which this entry's addressing information
        pertains.  The address type of this object is specified in
        npCfgIPAddrType."
::=  {  npCfgIPAddrEntry  3  }

npCfgIPAddrIfIndex	OBJECT-TYPE
        SYNTAX			InterfaceIndex
        MAX-ACCESS		read-only
        STATUS			current
        DESCRIPTION
        "Same as ifIndex."
::=  {  npCfgIPAddrEntry  4  }

npCfgIPAddrConfigBy	OBJECT-TYPE
        SYNTAX			INTEGER  { manual-one ( 1 ) , bootp-two ( 2 ) , manual-three ( 3 ) , bootp-four ( 4 ) , dhcpv4 ( 5 ) , not-configured ( 6 ) , default-config ( 7 ) , rarp ( 8 ) , read-only ( 9 ) , auto-ip ( 10 ) , dhcpv6 ( 11 ) , stateless ( 12 ) , linklocal ( 13 ) }
        MAX-ACCESS		read-only
        STATUS			current
        DESCRIPTION
        "This object indicates how the device obtained the
        corresponding IP address."
::=  {  npCfgIPAddrEntry  5  }

npCfgIPAddrStatus	OBJECT-TYPE
        SYNTAX			INTEGER  { undefined ( 0 ) , valid ( 1 ) , invalid ( 2 ) }
        MAX-ACCESS		read-only
        STATUS			current
        DESCRIPTION
        "Status of the associated IP Address."
::=  {  npCfgIPAddrEntry  6  }

npCfgIPAddrPrefixLength	OBJECT-TYPE
        SYNTAX			InetAddressPrefixLength
        MAX-ACCESS		read-only
        STATUS			current
        DESCRIPTION
        "The prefix length associated with this address."
::=  {  npCfgIPAddrEntry  7  }

npCfgIPAddrValidLifetime	OBJECT-TYPE
        SYNTAX			OCTET STRING
        MAX-ACCESS		read-only
        STATUS			current
        DESCRIPTION
        "Valid lifetime of this address. Only applicable
        to IPv6 addresses. The format is: {Never, 00d00h00m00s}
        where number of days can be upto 80 characters in length."
::=  {  npCfgIPAddrEntry  8  }

npCfgIPAddrPrefLifetime	OBJECT-TYPE
        SYNTAX			OCTET STRING
        MAX-ACCESS		read-only
        STATUS			current
        DESCRIPTION
        "Preferred lifetime of this address in seconds. Only applicable
        to IPv6 addresses. The format is: {Always, 00d00h00m00s}
        where number of days can be upto 80 characters in length."
::=  {  npCfgIPAddrEntry  9  }

npCfgIPv6DNSAddr1	OBJECT-TYPE
        SYNTAX			InetAddress
        MAX-ACCESS		read-write
        STATUS			current
        DESCRIPTION
        "IPv6 DNS Address, priority 1."
::=  {  npCfg  56  }

npCfgIPv6DNSAddr2	OBJECT-TYPE
        SYNTAX			InetAddress
        MAX-ACCESS		read-write
        STATUS			current
        DESCRIPTION
        "IPv6 DNS Address, priority 2."
::=  {  npCfg  57  }

npCfgIPConfigPrecedence	OBJECT-TYPE
        SYNTAX			OCTET STRING
        MAX-ACCESS		read-write
        STATUS			current
        DESCRIPTION
        "Allows to set uniform rules for parameter overwrite by
        different configuration methods.
        0 - Manual
        1 - TFTP
        2 - DHCPv4/Bootp
        3 - DHCPv6     - only if ipv6 is supported
        3/4 - Default  - 4 if ipv6 is supported otherwise 3
        The set string should be 0:1:2:3:4 (or 0:1:2:3 when ipv6 is not supported)
        or any colon separated combination of the 5 (or 4) integral values. The
        string should contain all integral values atleast and atmost once."
::=  {  npCfg  59  }

npCfgSTAWirelessMode 		OBJECT-TYPE
        SYNTAX			INTEGER  { b/g-Mode ( 0 ) , b/g/n-Mode ( 1 ) }
        MAX-ACCESS		read-write
        STATUS			current
        DESCRIPTION
        "Different standardized 802.11 wireless modes.
        The following values are defined:
        0 -  b/g/n-mode (Default)
        1 -  n-mode only
        Note: Guard Interval, AMSDU, Block Acknowledgement, and AMPDU are applicable in 802.11 n modes only.
        "
::=  {  npCfg  72  }

npCfgWirelessDirectSSIDSuffix			OBJECT-TYPE
        SYNTAX			OCTET STRING ( SIZE ( 1 .. 20  ) )
        MAX-ACCESS		read-write
        STATUS			current
        DESCRIPTION
        "
        The modifiable suffix of the network name (SSID) used by the uAP for Wireless Direct.
        The default is '<sub brand> <hp model>'. The value of this object is suffixed to the
        value of npCfgWirelessDirectSSIDPrefix to form the complete SSID.
        "
::=  {  npCfg  87  }

npCfgWirelessDirectSSIDPrefix			OBJECT-TYPE
        SYNTAX			OCTET STRING ( SIZE ( 1 .. 12  ) )
        MAX-ACCESS		read-only
        STATUS			current
        DESCRIPTION
        "
        The prefix of the network name (SSID) used by the uAP for Wireless Direct.
        The value is 'HP-Print-XY-' where XY is the last two hex characters from the
        wireless MAC address. The prefix is read-only. The value of this object is
        prefixed to the value of npCfgWirelessDirectSSIDSuffix to form the complete SSID.
        "
::=  {  npCfg  86  }

npCtlProtocolSet	OBJECT-TYPE
        SYNTAX			Integer32
        MAX-ACCESS		read-write
        STATUS			current
        DESCRIPTION
        "This is a 4 byte integer value.  The least significant bytes
        represent the protocols on the card.  A value of '1' indicates
        a protocol that is enabled.  A value of '0' indicates a
        protocol that is disabled.
        The 32-bit protocol enable 'structure' is defined as:
        bits 31-28:  Number of I/O channels/protocols present (NUM_CHAN)
        bits 27-24:  Number of I/O channels which may operate concurrently
        (NUM_OP_CHAN)
        bits 23-16:  unused, reserved
        bits 15-1:   Individual I/O channel/protocol enable bits,
        0 == disable, 1 == enable
        MIO_IOCHAN_NOVELL   bit   1
        MIO_IOCHAN_LLC      bit   2
        MIO_IOCHAN_TCP      bit   3
        MIO_IOCHAN_ATALK    bit   4
        MIO_IOCHAN_IPV6	bit   5
        bit  0:      When NUM_OP_CHAN == 1, auto-protocol select enable bit,
        0 == disable, 1 == enable  (APS_ON)"
::=  {  npCtl  9  }

npCtlSLP	OBJECT-TYPE
        SYNTAX			Integer32  ( 0 .. 1  )
        MAX-ACCESS		read-write
        STATUS			current
        DESCRIPTION
        "Configure Service Location Protocol (SLP) service.
        (0) = SLP disabled
        (1) = SLP enabled"
::=  {  npCtl  21  }

npCtlLPD	OBJECT-TYPE
        SYNTAX			Integer32  ( 0 .. 1  )
        MAX-ACCESS		read-write
        STATUS			current
        DESCRIPTION
        "Configure Line Printer Daemon Protocol (LPD) service.
        (0) = LPD disabled
        (1) = LPD enabled"
::=  {  npCtl  22  }

npCtl9100	OBJECT-TYPE
        SYNTAX			Integer32  ( 0 .. 1  )
        MAX-ACCESS		read-write
        STATUS			current
        DESCRIPTION
        "Configure TCP port 9100 printing.
        (0) = port 9100 printing disabled
        (1) = port 9100 printing enabled"
::=  {  npCtl  24  }

npCtlSnmpVersionAccess	OBJECT-TYPE
        SYNTAX			INTEGER  { snmpV1RW-snmpV3RW ( 1 ) , snmpV1RO-snmpV3RW ( 2 ) , snmpV1NoAccess-snmpV3RW ( 3 ) , snmpV1RW-snmpV3NoAccess ( 4 ) ,snmpV1RO-snmpV3NoAccess ( 5 ) }
        MAX-ACCESS		read-write
        STATUS			current
        DESCRIPTION
        "Manages an SNMP version's read and write access to the MIB."
::=  {  npCtl  27  }

npCtlSnmpV3InitAccount	OBJECT-TYPE
        SYNTAX			INTEGER  { Destroy ( 0 ) , blockInitEncrypt ( 4 ) }
        MAX-ACCESS		read-write
        STATUS			current
        DESCRIPTION
        "Used to create initial SNMPv3 account.  The following rules apply:
        0 = clear init account, only if previously 0.
        4 = Block init account, only cold reset will clear or use Web User interface.
        Setting this object to blocked (4) will block an initial account
        creation until a cold reset."
::=  {  npCtl  28  }

npCtlBonjour	OBJECT-TYPE
        SYNTAX			Integer32  ( 0 .. 1  )
        MAX-ACCESS		read-write
        STATUS			current
        DESCRIPTION
        "Configure Multicast Domain Name Service.
        (0) = Bonjour disabled
        (1) = Bonjour enabled"
::=  {  npCtl  29  }

npCtlNetworkConnectionMode	OBJECT-TYPE
        SYNTAX			INTEGER  { auto-cable-detect ( 1 ) , disable-radio ( 2 ) , disable-wired ( 3 ) }
        MAX-ACCESS		read-write
        STATUS			current
        DESCRIPTION
        "This object controls the selection of the active network
        interface used for communication. This is applicable to
        products supporting dual wired and wireless network interfaces"
::=  {  npCtl  32  }

npCtlWSDiscovery	OBJECT-TYPE
        SYNTAX			INTEGER  { disable ( 0 ) , enable ( 1 ) }
        MAX-ACCESS		read-write
        STATUS			current
        DESCRIPTION
        "Web Services Discovery enable/disable."
::=  {  npCtl  36  }

npCtlWSPrint		OBJECT-TYPE
        SYNTAX			INTEGER  { disable ( 0 ) , enable ( 1 ) }
        MAX-ACCESS		read-write
        STATUS			current
        DESCRIPTION
        "Web Services Print enable/disable."
::=  {  npCtl  37  }

npCtlWPAD		OBJECT-TYPE
        SYNTAX			INTEGER  { disable ( 0 ) , automatic-Web-Proxy ( 1 ) , manual-url ( 2 ) , manual-proxy-settings ( 3 ) }
        MAX-ACCESS		read-write
        STATUS			current
        DESCRIPTION
        " Used to Disable and Enable Web-Proxy Auto Discovery."
::=  {  npCtl  39  }

npCtlFpDot11WirelessState	OBJECT-TYPE
        SYNTAX			INTEGER  { Disable ( 0 ) , Enable ( 1 )}
        MAX-ACCESS		read-write
        STATUS			current
        DESCRIPTION
        "Use for enabling and disabling Wireless Radio.
        The following values are defined:
        Disable		= 0
        Enable		= 1
        Default		= 1(Enabled)"
::=  {  npCtl  47 }

npCtlDot11nSTAGuardInterval 		OBJECT-TYPE
        SYNTAX			INTEGER  { Auto ( 0 ) , Short ( 1 ) , Long ( 2 ) }
        MAX-ACCESS		read-write
        STATUS			current
        DESCRIPTION
        "The guard interval is the space between symbols (characters) being transmitted.
        The guard interval is there to eliminate intersymbol interference, which is referred to as ISI.
        ISI happens when echoes or reflections from one symbol interfere with another. Adding time between
        symbol transmissions allows these echoes and 	reflections to settle in before the next symbol is transmitted.
        Short Guard Interval increases the data rate by roughly 10-11%.
        The following values are defined:
        0 - Auto (default)
        1 - Short
        2 - Long
        "
::=  {  npCtl  51  }

npCtlDot11nSTAAMSDUAggregation		OBJECT-TYPE
        SYNTAX			INTEGER  { Disable ( 0 ) , Enable ( 1 ) }
        MAX-ACCESS		read-write
        STATUS			current
        DESCRIPTION
        "802.11n can send multiple frames per single access to the medium by combining frames together into one larger frame.
        There are two forms of frame aggregation:
        Aggregated Mac Service Data Unit (A-MSDU) and Aggregated Mac Protocol Data Unit (A-MPDU).
        A-MSDU increases the maximum frame transmission size from 2,304 bytes to almost 8k bytes (7935 to be exact)
        while A-MPDU allows up to 64k bytes. A-	MSDU creates the larger frame by combining smaller frames with
        the same physical source and destination end points and traffic class (i.e. QoS) into one large frame with a common MAC header.
        Disable				= 0
        Enable(Default)		= 1
        "
::=  {  npCtl  52 }

npCtlDot11nSTABlockACKs		OBJECT-TYPE
        SYNTAX			INTEGER  { Disable ( 0 ) , Enable ( 1 )}
        MAX-ACCESS		read-write
        STATUS			current
        DESCRIPTION
        "This mechanism allows each of the aggregated data frames to be individually acknowledged or
        retransmitted if affected by an error. Block acknowledgement compiles all the acknowledgements
        of the individual constituent frames produced by MPDU aggregation into a single frame returned
        by the recipient to the sender. This allows a compact and rapid mechanism to implement selective
        retransmission of only those constituent frames that are not acknowledged.
        Disable				= 0
        Enable(Default)		= 1
        "
::=  {  npCtl  53 }

npCtlDot11nSTAAMPDUAggregation		OBJECT-TYPE
        SYNTAX			INTEGER  { Disable ( 0 ) , Enable ( 1 ) }
        MAX-ACCESS		read-write
        STATUS			current
        DESCRIPTION
        "802.11n can send multiple frames per single access to the medium by combining frames together into one larger frame.
        There are two forms of frame aggregation:
        Aggregated Mac Service Data Unit (A-MSDU) and Aggregated Mac Protocol Data Unit (A-MPDU).
        A-MSDU increases the maximum frame transmission size from 2,304 bytes to almost 8k bytes (7935 to be exact)
        while A-MPDU allows up to 64k bytes. A-	MSDU creates the larger frame by combining smaller frames with
        the same physical source and destination end points and traffic class (i.e. QoS) into one large frame with a common MAC header.
        Disable				= 0
        Enable(Default)		= 1
        "
::=  {  npCtl  54 }

npCtlWirelessDirectSSIDBroadcast		OBJECT-TYPE
        SYNTAX			INTEGER  { not-allowed ( 0 ) , allowed ( 1 ) }
        MAX-ACCESS		read-write
        STATUS			current
        DESCRIPTION
        "This is used to allow or hide broadcasting of the SSID by the uAP.
        Allowed(Default) = 1
        Not Allowed      = 0
        "
::=  {  npCtl  57 }

npCtlWirelessDirectHidePassphrase  		OBJECT-TYPE
        SYNTAX			INTEGER  { show ( 0 ) , hide ( 1 ) }
        MAX-ACCESS		read-write
        STATUS			obsolete
        DESCRIPTION
        "
        This controls display of the Wireless Direct passphrase on configuration reports/pages  or on the control panel.
        Show = 0
        Hide = 1
        Note: This OID is not yet implemented and has been added to reserve the OID number for future purposes
        as the number has already been shared with other teams.
        "
::=  {  npCtl  58 }

npCtlDeviceMode		OBJECT-TYPE
        SYNTAX			INTEGER  { WiredStationMode ( 1 ) , WirelessStationMode ( 2 ) , AccessPointMode (3) }
        MAX-ACCESS		read-only
        STATUS			current
        DESCRIPTION
        " Use to check the current state of the device.
        WiredStationMode			= 1
        WirelessStationMode			= 2
        AccessPointMode				= 3
        "
::=  {  npCtl  67 }

npCtlWirelessSTAState  OBJECT-TYPE
        SYNTAX      INTEGER  { disabled ( 0 ), enabled ( 1 ) }
        MAX-ACCESS  read-write
        STATUS      current
        DESCRIPTION
        "Configure 802.11 wireless station (STA) functionality
        0 = Wireless station is disabled
        1 = Wireless station is enabled
        "
::=  {  npCtl  73 }

npCtlWirelessDirectState   OBJECT-TYPE
        SYNTAX      INTEGER  { disabled ( 0 ), enabled ( 1 ) }
        MAX-ACCESS  read-write
        STATUS      current
        DESCRIPTION
        "Configure 802.11 wireless direct (uAP) functionality
        0 = Wireless Direct is disabled
        1 = Wireless Direct is enabled
        "
::=  {  npCtl  74 }

npNpiPaeClass	OBJECT-TYPE
        SYNTAX			INTEGER  { printer ( 1 ) , plotter ( 2 ) , xStation ( 3 ) }
        MAX-ACCESS		read-only
        STATUS			current
        DESCRIPTION
        "The class assigned to the peripheral onto which
        this card is plugged."
::=  {  npNpiPeripheralAttributeEntry  2  }

npNpiPaeIdentification	OBJECT-TYPE
        SYNTAX			INTEGER  { laserjet-IIISI ( 1 ) , laserjet-4SI ( 5 ) }
        MAX-ACCESS		read-only
        STATUS			current
        DESCRIPTION
        "The Identification number of the peripheral.  These values are
        defined in the MIO spec.  DesignJet, PaintJet XL300, and
        DesignJet/600 peripherals will identify themselves as
        LaserJet-IIIsi."
::=  {  npNpiPeripheralAttributeEntry  3  }

npNpiCaeClass	OBJECT-TYPE
        SYNTAX			INTEGER  { rs-232 ( 1 ) , centronics ( 2 ) , csma-cd-network ( 3 ) , token-ring-network ( 4 ) , scsi ( 5 ) , hpib ( 6 ) , localtalk ( 7 ) , hpna ( 8 ) , usb ( 9 ) , firewire ( 10 ) , bluetooth ( 11 ) , ieee802-11b ( 12 ) }
        MAX-ACCESS		read-only
        STATUS			current
        DESCRIPTION
        "The class of this network peripheral card."
::=  {  npNpiCardAttributeEntry  2  }

npIpxSapInfo	OBJECT-TYPE
        SYNTAX			OCTET STRING
        MAX-ACCESS		read-only
        STATUS			current
        DESCRIPTION
        "This is a 50 byte array that contains the following
        information.
        2 bytes:  bindery object type (always 030c in hi-lo order)
        12 bytes:  Mac address of card (ASCII)
        2 bytes:  frame type
        also high bit (8000) is set if card is not configured
        2 bytes : unit type (hex 81 for NetJet card)
        32 bytes: node name (ASCII) which is:
        print server name for Queue Server mode
        printer name for RPTR mode"
::=  {  npIpx  6  }

npIpxGetUnitCfgResp2	OBJECT-TYPE
        SYNTAX			OCTET STRING
        MAX-ACCESS		read-only
        STATUS			current
        DESCRIPTION
        "This object is the Get Unit Config Response
        structure described in the IPX code.  This
        structure is of variable length depending
        on how many servers are configured.  This is
        the second set of info when more than
        8 print servers are configured."
::=  {  npIpx  7  }

npIpxRcfgAddress	OBJECT-TYPE
        SYNTAX			OCTET STRING  ( SIZE ( 12  ) )
        MAX-ACCESS		read-only
        STATUS			current
        DESCRIPTION
        "The 12 octet IPX address of the Novell RCFG socket.  The address
        is in network byte order."
::=  {  npIpx  13  }

npPortNumPorts	OBJECT-TYPE
        SYNTAX			Integer32  ( 0 .. 255  )
        MAX-ACCESS		read-only
        STATUS			current
        DESCRIPTION
        "The number of peripheral interfaces supported by this device."
::=  {  npPort  1  }

npWebProxyServerId	OBJECT-TYPE
        SYNTAX			OCTET STRING  ( SIZE ( 0 .. 255  ) )
        MAX-ACCESS		read-write
        STATUS			current
        DESCRIPTION
        "IP address or hostname of web proxy server."
::=  {  npWeb  12  }

npWebProxyServerPort	OBJECT-TYPE
        SYNTAX			Integer32
        MAX-ACCESS		read-write
        STATUS			current
        DESCRIPTION
        "IP port of web proxy server"
::=  {  npWeb  13  }

npWebProxyUserName	OBJECT-TYPE
        SYNTAX			OCTET STRING  ( SIZE ( 0 .. 64  ) )
        MAX-ACCESS		read-write
        STATUS			current
        DESCRIPTION
        "Proxy web user identification"
::=  {  npWeb  14  }

npWebProxyUserPasswd	OBJECT-TYPE
        SYNTAX			OCTET STRING  ( SIZE ( 0 .. 32  ) )
        MAX-ACCESS		read-write
        STATUS			current
        DESCRIPTION
        "Proxy web user password"
::=  {  npWeb  15  }

npSecurityDot11ServerAuthentication	OBJECT-TYPE
        SYNTAX			INTEGER  { eap-md5 ( 1 ) , eap-tls ( 2 ) , leap ( 4 ) , peap ( 8 ) , ttls ( 16 ) }
        MAX-ACCESS		read-write
        STATUS			current
        DESCRIPTION
        "Server-Based Authentication with the following bitwise values:
        None(0),
        EAP-MD5(1),
        EAP-TLS(2),
        LEAP(4),
        PEAP(8),
        TTLS(16)"
::=  {  npSecurity  1  }

npSecurityDot1xEapMd5Identity	OBJECT-TYPE
        SYNTAX			OCTET STRING  ( SIZE ( 0 .. 130  ) )
        MAX-ACCESS		read-write
        STATUS			current
        DESCRIPTION
        "Radius MD5 authentication User Name."
::=  {  npSecurity  2  }

npSecurityDot1xTLSAuthServerId	OBJECT-TYPE
        SYNTAX			OCTET STRING  ( SIZE ( 0 .. 64  ) )
        MAX-ACCESS		read-write
        STATUS			current
        DESCRIPTION
        "TLS authentication Server ID."
::=  {  npSecurity  3  }

npSecurityPublicKey	OBJECT-TYPE
        SYNTAX			OCTET STRING  ( SIZE ( 0 .. 64  ) )
        MAX-ACCESS		read-only
        STATUS			current
        DESCRIPTION
        "The public key of a public/private key pair to be
        used by applications to set encrypted values."
::=  {  npSecurity  4  }

npSecurityDot11EncryptedDot11NetworkName	OBJECT-TYPE
        SYNTAX			OCTET STRING  ( SIZE ( 0 .. 130  ) )
        MAX-ACCESS		write-only
        STATUS			current
        DESCRIPTION
        "The encrypted network name (SSID).  Use the
        npSecurityPublicKey to encrypt this value.
        Setting this object will cause the card to reconfigure."
::=  {  npSecurity  5  }

npSecurityDot11EncryptedDot1xEapMd5Secret	OBJECT-TYPE
        SYNTAX			OCTET STRING  ( SIZE ( 0 .. 130  ) )
        MAX-ACCESS		write-only
        STATUS			current
        DESCRIPTION
        "The encrypted dot1xEapMD5Secret authentication password.
        Use the npSecurityPublicKey to encrypt this value.
        Setting this object will cause the card to reconfigure."
::=  {  npSecurity  6  }

npSecurityDot11SignalStrength	OBJECT-TYPE
        SYNTAX			INTEGER  { level-1-TBD ( 1 ) , level-2-TBD ( 2 ) , level-3-TBD ( 3 ) , level-4-TBD ( 4 ) , level-5-TBD ( 5 ) }
        MAX-ACCESS		read-only
        STATUS			current
        DESCRIPTION
        "A weighted average over time of the signal strength
        between the access point and the print server in infrastructure
        mode. Not applicable when in ad hoc mode."
::=  {  npSecurity  8  }

npSecurityDot11SSID	OBJECT-TYPE
        SYNTAX			OCTET STRING  ( SIZE ( 0 .. 32  ) )
        MAX-ACCESS		read-only
        STATUS			current
        DESCRIPTION
        "A discovered SSID value."
::=  {  npSecurityDot11SSIDEntry  2  }

npSecurityDot11SSIDTableNumEntries	OBJECT-TYPE
        SYNTAX			Integer32
        MAX-ACCESS		read-only
        STATUS			current
        DESCRIPTION
        "Displays the number of discovered SSIDs in
        the SSID Table."
::=  {  npSecurity  10  }

npSecurityDot11SSLCertLoaded	OBJECT-TYPE
        SYNTAX			INTEGER  { true ( 1 ) , false ( 2 ) }
        MAX-ACCESS		read-only
        STATUS			current
        DESCRIPTION
        "Indicates if SSL certificate has been loaded."
::=  {  npSecurity  11  }

npSecurityDot11TLSCertLoaded	OBJECT-TYPE
        SYNTAX			INTEGER  { true ( 1 ) , false ( 2 ) }
        MAX-ACCESS		read-only
        STATUS			current
        DESCRIPTION
        "Indicates if TLS Trusted CA certificate has been loaded."
::=  {  npSecurity  12  }

npSecuritySnmpV3EncryptedUserName	OBJECT-TYPE
        SYNTAX			OCTET STRING  ( SIZE ( 256 ) )
        MAX-ACCESS		write-only
        STATUS			current
        DESCRIPTION
        "The encrypted SNMPv3 User Name.
        Use the npSecurityPublicKey to encrypt this value.
        The new SNMPv3 User Account will be installed after the
        npSecuritySnmpV3EncryptedUserName, npSecuritySnmpV3AuthKeyPassPhrase
        and npSecuritySnmpV3PrivKeyPassPharse have been set."
::=  {  npSecurity  13  }

npSecuritySnmpV3AuthKeyPassPhrase	OBJECT-TYPE
        SYNTAX			OCTET STRING  ( SIZE ( 256 ) )
        MAX-ACCESS		write-only
        STATUS			current
        DESCRIPTION
        "The encrypted SNMPv3 Authentication passphrase or key .
        Use the npSecurityPublicKey to encrypt this value.
        The new SNMPv3 User Account will be installed after the
        npSecuritySnmpV3EncryptedUserName, npSecuritySnmpV3AuthKeyPassPhrase
        and npSecuritySnmpV3PrivKeyPassPharse have been set.
        Set npSecuritySnmpV3AuthAlgorithm, npSecuritySnmpV3PrivAlgorithm and npSecuritySnmpV3PassPhrase
        to the required values before setting this OID.
        "
::=  {  npSecurity  14  }

npSecuritySnmpV3PrivKeyPassPharse	OBJECT-TYPE
        SYNTAX			OCTET STRING  ( SIZE ( 256 ) )
        MAX-ACCESS		write-only
        STATUS			current
        DESCRIPTION
        "The encrypted SNMPv3 Privacy passphrase or key.
        Use the npSecurityPublicKey to encrypt this value.
        The new SNMPv3 User Account will be installed after the
        npSecuritySnmpV3EncryptedUserName, npSecuritySnmpV3AuthKeyPassPhrase
        and npSecuritySnmpV3PrivKeyPassPharse have been set.
        Set npSecuritySnmpV3AuthAlgorithm, npSecuritySnmpV3PrivAlgorithm and npSecuritySnmpV3PassPhrase
        to the required values before setting this OID.
        "
::=  {  npSecurity  15  }

npSecurityDot11ExactMatchServerId	OBJECT-TYPE
        SYNTAX			INTEGER  { true ( 1 ) , false ( 2 ) }
        MAX-ACCESS		read-write
        STATUS			current
        DESCRIPTION
        "Indicates if an exact match is required on the EAP Server ID."
::=  {  npSecurity  19  }

npSecurityDot11EncryptionStrength	OBJECT-TYPE
        SYNTAX			INTEGER  { low ( 1 ) , medium ( 2 ) , high ( 3 ) }
        MAX-ACCESS		read-write
        STATUS			current
        DESCRIPTION
        "Indicates the EAP encrytpion strength."
::=  {  npSecurity  20  }

npSecurityCertBuff	OBJECT-TYPE
        SYNTAX			OCTET STRING  ( SIZE ( 512  ) )
        MAX-ACCESS		read-only
        STATUS			current
        DESCRIPTION
        "A 512 byte buffer of the print server certificate as indexed by
        npSecurityCertBuffIndex."
::=  {  npSecurity  21  }

npSecurityCertBuffIndex	OBJECT-TYPE
        SYNTAX			INTEGER  { block1 ( 1 ) , block2 ( 2 ) , block3 ( 3 ) , block4 ( 4 ) , block5 ( 5 ) , block6 ( 6 ) }
        MAX-ACCESS		read-write
        STATUS			current
        DESCRIPTION
        "Indicates the index of the 512 byte block of the print server
        certificate to load into npSecurityCertBuff."
::=  {  npSecurity  22  }

npSecuritySslRedirection	OBJECT-TYPE
        SYNTAX			INTEGER  { redirectionEnabled ( 1 ) , redirectionDisabled ( 2 ) }
        MAX-ACCESS		read-write
        STATUS			current
        DESCRIPTION
        "Setting this object causes the SSL redirection connection
        to be enabled or disabled."
::=  {  npSecurity  23  }

npSecurityReset	OBJECT-TYPE
        SYNTAX			INTEGER  { Set ( 0 ) , Reset ( 1 ) }
        MAX-ACCESS		read-write
        STATUS			current
        DESCRIPTION
        "Setting this object causes security object to reset bact to the defaults."
::=  {  npSecurity  24  }

npSecurityDot11WEPStrength	OBJECT-TYPE
        SYNTAX			INTEGER  { not-set ( 1 ) , strenth-40-bit ( 2 ) , strenth-104-bit ( 3 ) }
        MAX-ACCESS		read-only
        STATUS			current
        DESCRIPTION
        "Indicates the encryption strength of the WEP keys."
::=  {  npSecurity  26  }

npSecurityServicesSupported	OBJECT-TYPE
        SYNTAX			Integer32
        MAX-ACCESS		read-only
        STATUS			current
        DESCRIPTION
        "BITWISE indication of the 802.11 security services this device supports.
        The following bits are defined:
        MD5       						(0)
        TLS       						(1)
        TTLS      						(2)
        LEAP      						(3)
        PEAP      						(4)
        Reserved  						(5 - 15)
        WEP       						(16)
        WPA       						(17)
        AES       						(18)
        WPA2      						(19)
        AUTO_FOR_WEP_SUPPORTED      	(20)
        AUTO_FOR_WPA_SUPPORTED      	(21)
        AUTO_FOR_ENCRYPTION_SUPPORTED   (22)
        Reserved  (23 - 31)"
::=  {  npSecurity  27  }

npSecurityDot11Encryption	OBJECT-TYPE
        SYNTAX			Integer32
        MAX-ACCESS		read-write
        STATUS			current
        DESCRIPTION
        "802.11 encryption method currently enabled.
        The following values are defined:
        NONE       (0x00)
        SSN/WEP    (0x01)
        TKIP       (0x02)
        AES        (0x03)
        AUTO       (0x04)
        Reserved  (5 - 31)
        It is advised not to use dot11PrivacyInvoked OID anymore, instead use npSecurityDot11Encryption.
        Since Jetdirect updates the same variable when the set happens through any of the two OIDs and
        npSecurityDot11Encryption is more versatile, it is recommended to use this OID.
        "
::=  {  npSecurity  28  }

npSecurityDot11MulticastCipher	OBJECT-TYPE
        SYNTAX			Integer32
        MAX-ACCESS		read-write
        STATUS			current
        DESCRIPTION
        "BITWISE indication of the multicast cipher method currently enabled.
        At minimum, one bit must be set.
        The following bits are defined:
        WEP       (0)
        WPA       (1)
        Reserved  (2 - 31)"
::=  {  npSecurity  29  }

npSecurityDot11BeaconInfoXMLString	OBJECT-TYPE
        SYNTAX			OCTET STRING  ( SIZE ( 0 .. 512  ) )
        MAX-ACCESS		read-only
        STATUS			current
        DESCRIPTION
        "This object returns an XML encoded string with information about
        the discovered BSSID."
::=  {  npSecurityDot11BeaconEntry  2  }

npSecurityDot11BeaconTableNumEntries	OBJECT-TYPE
        SYNTAX			Integer32
        MAX-ACCESS		read-only
        STATUS			current
        DESCRIPTION
        "Displays the number of discovered SSIDs in the DOT11 Beacon Table."
::=  {  npSecurity  34  }

npSecurityDot11OpenSSIDEnabled	OBJECT-TYPE
        SYNTAX			TruthValue
        MAX-ACCESS		read-only
        STATUS			current
        DESCRIPTION
        "Indicates if the Open SSID is enabled (Spirit-only)."
::=  {  npSecurity  35  }

npSecurityDot11DynamicEncryption	OBJECT-TYPE
        SYNTAX			INTEGER  { NONE ( 0 ) , BASIC ( 1 ) , WPA ( 2 ) , WPA2 ( 3 ) , AUTO ( 4 ) }
        MAX-ACCESS		read-write
        STATUS			current
        DESCRIPTION
        "WPA mode.
        (0x00) = NONE
        (0x01) = BASIC
        (0x02) = WPA
        (0x03) = WPA2
        (0x04) = AUTO"
::=  {  npSecurity  42  }

npSecurityDot11LinkAuthentication	OBJECT-TYPE
        SYNTAX			INTEGER  { open ( 1 ) , shared-key ( 2 ) , leap ( 128 ) , auto ( 143 ) }
        MAX-ACCESS		read-write
        STATUS			current
        DESCRIPTION
        "DOT11 Link Authentication modes.
        (1) = OPEN
        (2) = SHARED-KEY
        (128) = LEAP
        (143) = AUTO
        We can set the Link Authentication using the object dot11AuthenticationAlgorithmsEnable ( OID: 1.2.840.10036.1.2.1.3.x )
        Since the dot11AuthenticationAlgorithsmEnable object does not supports setting of AUTO option, we provide this object.
        Through this OID you can set to any one of the above options.
        Whereas using the dot11AuthenticationAlgorithmsEnable object we can set either OPEN OR SHARED mode only."
::=  {  npSecurity  43 }

npSecuritySnmpV3AuthAlgorithm	OBJECT-TYPE
        SYNTAX			INTEGER  { md5 ( 2 ), sha-1 ( 3 ) }
        MAX-ACCESS		read-write
        STATUS			current
        DESCRIPTION
        "Indicates the Authentication Algorithm used.
        It can have the value MD5 or SHA-1.
        This key will have a default value set to MD5.
        The following values are defined:
        MD5    2 (Default)
        SHA-1  3
        "
::=  {  npSecurity  44 }

npSecuritySnmpV3PrivAlgorithm	OBJECT-TYPE
        SYNTAX			INTEGER  { des ( 2 ), aes-128 ( 3 ) }
        MAX-ACCESS		read-write
        STATUS			current
        DESCRIPTION
        "Indicates the Privacy Algorithm used.
        It can have the value DES or AES-128.
        This key will have a default value set to DES.
        The following values are defined:
        DES       2 (Default)
        AES-128   3
        "
::=  {  npSecurity  45 }

npSecuritySnmpV3PassPhrase	OBJECT-TYPE
        SYNTAX			INTEGER  { key ( 0 ), passphrase ( 1 ) }
        MAX-ACCESS		read-write
        STATUS			current
        DESCRIPTION
        "Indicates whether npSecuritySnmpV3AuthKeyPassPhrase and npSecuritySnmpV3PrivKeyPassPharse OIDs
        will have Passphrase or key value.
        Key Value    0
        Passphrase   1
        "
::=  {  npSecurity  46 }

npSecurityWirelessDirectEncryptionMethod	OBJECT-TYPE
        SYNTAX		INTEGER  { noSecurity ( 1 ) , wpa ( 2 ) }
        MAX-ACCESS		read-write
        STATUS			current
        DESCRIPTION
        "This is used to select the encryption protocol in Wireless Direct Mode.
        The following values are defined:
        No Security     ( 1 )
        WPA             ( 2 )
        "
::=  {  npSecurity  51  }

npSecurityWirelessDirectEncryptedPassPhrase		OBJECT-TYPE
        SYNTAX			OCTET STRING  ( SIZE ( 1 .. 64  ) )
        MAX-ACCESS		write-only
        STATUS			current
        DESCRIPTION
        "
        The WPA2 Passphrase or pre-shared key for secure Wireless Direct.
        The values allowed are 8 to 63 printable ASCII characters for passphrase
        or a 64 character hex value for pre-shared key.
        Use npSecurityPublicKey to encrypt this value.
        "
::=  { npSecurity  55 }

npSecurityDot1xFailSafe		OBJECT-TYPE
        SYNTAX                      INTEGER  { Enable ( 1 ) , Disable ( 0 ) }
        MAX-ACCESS                  read-write
        STATUS                      current
        DESCRIPTION
        "After configuring 802.1x on the printer and switching it over to a secured network, if authentication is
        successful printer retains connectivity and if it fails it loses connectivity.
        In case of authentication failure, it does not acquire connectivity even when switched over to an unsecured network.
        802.1x failsafe is a feature which allows printer to retain connectivity in a unsecured network even if authentication fails.
        Setting this OID to 1 enables this feature and setting to 0 disables this feature.
        Connect anyway (802.1x Fail-Safe)           ( 1 )
        Block network  (secure failure)             ( 0 )
        "
::=  { npSecurity  57 }

npSecuritySSLProtocol		OBJECT-TYPE
        SYNTAX                      INTEGER
        MAX-ACCESS                  read-write
        STATUS                      current
        DESCRIPTION
        "
        Different SSL Protocols can be selected with the following bitwise values:
        SSL 3.0 (1)
        TLS 1.0 (2)
        TLS 1.1 (4)
        TLS 1.2 (8)
        "
::=  { npSecurity  58 }

setCommunityName	OBJECT-TYPE
        SYNTAX			OCTET STRING  ( SIZE ( 0 .. 255  ) )
        MAX-ACCESS		read-write
        STATUS			current
        DESCRIPTION
        "This object controls access of snmp read-write requests.  Factory
        default configuration provides authentication of incoming packets
        with community names: internal and public.  This object overrides the
        factory default settings so that the factory default setttings no longer
        work. This object returns SET or NOT_SET."
::=  {  community  1  }

getCommunityName	OBJECT-TYPE
        SYNTAX			OCTET STRING  ( SIZE ( 0 .. 255  ) )
        MAX-ACCESS		read-write
        STATUS			current
        DESCRIPTION
        "This object controls access of snmp read requests.  Factory
        default configuration provides authentication of incoming packets
        with community names: internal and public.  This object provides
        access in addition to the factory default settings. If
        set, then authentication will succeed with any of the following
        community names: internal, public, getCommunityName, or
        setCommunityName. This object returns SET or NOT_SET."
::=  {  community  2  }

ppmGeneralNaturalLanguage OBJECT-TYPE
        SYNTAX      SnmpAdminString (SIZE (0..63))
        MAX-ACCESS  read-only
        STATUS      current
        DESCRIPTION
        "The natural language tag (RFC 3066), specified in US-ASCII, for
        all localized text string objects defined in this MIB (syntax of
        'SnmpAdminString'), or the empty string if not specified.  For
        example, 'fr-CH' (French as written in Switzerland).
        Compatibility Note:  At the time of publication of this MIB,
        language tags are restricted to US-ASCII.  In order to support
        possible future evolution of languages tags (in a successor to
        RFC 3066) to allow non-ASCII characters, this object has been
        defined with a syntax of UTF-8 (RFC 3629).
        This natural language tag is necessary for support of correct
        glyph selection for text display, for support of text-to-
        speech, for support of correct sorting of text values, etc.
        If this object is empty, then the natural language for all
        localized text string objects in this MIB MUST default to
        'en-US' (US English)."
        REFERENCE
        "prtGeneralCurrentLocalization in IETF Printer MIB (RFC
        1759/3805).
        jobNaturalLanguageTag in IETF Job Monitoring MIB (RFC 2707)."
        DEFVAL      { ''H }                 -- no natural language tag
::= { ppmGeneral 1 }

ppmGeneralNumberOfPrinters OBJECT-TYPE
        SYNTAX      Gauge32
        MAX-ACCESS  read-only
        STATUS      current
        DESCRIPTION
        "The number of printers supported on this network system,
        i.e., the number of entries in the 'ppmPrinterTable' below, or
        zero if no printers are currently configured."
        DEFVAL      { 0 }                   -- no printers configured
::= { ppmGeneral 2 }

ppmGeneralNumberOfPorts OBJECT-TYPE
        SYNTAX      Gauge32
        MAX-ACCESS  read-only
        STATUS      current
        DESCRIPTION
        "The number of printer ports supported on this network system,
        i.e., the number of entries in the 'ppmPortTable' below, or
        zero if no printer ports are currently configured."
        DEFVAL      { 0 }                   -- no printer ports configured
::= { ppmGeneral 3 }

ppmPrinterName OBJECT-TYPE
        SYNTAX      SnmpAdminString (SIZE (0..127))
        MAX-ACCESS  read-only
        STATUS      current
        DESCRIPTION
        "A user friendly name for this printer that may be used to
        facilitate user selection of a printer supported by a network
        system, in the locale specified by 'ppmGeneralNaturalLanguage'.
        This printer name may contain non-ASCII characters that are NOT
        allowed in a URI (RFC 3986) without percent-encoding.
        Systems that implement the IETF Printer MIB v1 (RFC 1759) SHOULD
        implement this object as an augmentation to the Printer MIB v1.
        Systems that implement the IETF Printer MIB v2 (RFC 3805) MUST
        ensure that the value of this object is identical to the value
        of 'prtGeneralPrinterName' for each printer.
        The value of this object SHOULD be unique across all printers on
        this network system and SHOULD be meaningful to end users
        (e.g., 'PrinterXYZ').
        The value of this object SHOULD be set by an out-of-band method
        (e.g., local console) during installation (by the vendor or site
        administrator) and SHOULD NOT be subsequently modified, so that
        the value can be used as a static key for access to the printer.
        The charset of this text string object is UTF-8 (RFC 3629), in
        order to support names that cannot be represented in US-ASCII."
        REFERENCE
        "prtGeneralPrinterName in IETF Printer MIB v2 (RFC 3805).
        printer-name in IPP/1.1 (RFC 2911)."
        DEFVAL      { ''H }                 -- printer name not specified
::= { ppmPrinterEntry 2 }

ppmPrinterIEEE1284DeviceId OBJECT-TYPE
        SYNTAX      OCTET STRING (SIZE (0..1023))
        MAX-ACCESS  read-only
        STATUS      current
        DESCRIPTION
        "The IEEE 1284 device ID for this printer, a set of capabilities
        (keys and values) specified in the US-ASCII charset and the
        format 'key1: value {, value }; ... keyN: value {,value };',
        as follows:
        (a) SPACE (0x20), TAB (0x09), VTAB (0x0B), CR (0x0D), NL (0x0A),
        and FF (0x0C) are allowed, but are ignored when parsing
        (b) other control characters (less than 0x20) MUST NOT be used
        (c) COLON (0x3A), COMMA (0x2C), and SEMICOLON (0x3B) are used as
        delimiters and MUST NOT be included in any key or value
        (d) each key MUST be separated from value(s) using COLON (0x3A)
        (e) multiple values MUST BE separated using COMMA (0x2C)
        (f) each capability MUST BE terminated using SEMICOLON (0x3B)
        (g) all printers MUST include the following capabilities
        - MANUFACTURER (or abbreviation MFG)
        - MODEL (or abbreviation MDL)
        (h) all printers MAY include the following capabilities
        - COMMAND SET (or abbreviation CMD)
        - COMMENT
        - ACTIVE COMMAND SET
        For example (actually all on one line of text):
        MANUFACTURER:ACME Manufacturing;
        COMMAND SET:PCL,PJL,PS,XHTML-Print+xml;
        MODEL:LaserBeam 9;
        COMMENT:Anything you like;
        ACTIVE COMMAND SET:PCL;
        The value of this object MUST exactly match the IEEE 1284-2000
        Device ID string, except that the length field MUST NOT be
        specified.  The value MUST be assigned by the Printer vendor
        and MUST NOT be localized by the Print Service.
        Compatibility Note:  At the time of publication of this MIB,
        IEEE device IDs are restricted to US-ASCII.  In order to support
        possible future evolution of IEEE device IDs (in a successor to
        IEEE 1284-2000) to allow non-ASCII characters, this object has
        been defined with a syntax of OCTET STRING to support the future
        use of UTF-8 (RFC 3629).
        If this object is empty, then the value of 'ppmPortProtocolType'
        for the selected port SHOULD be used to load a generic driver."
        REFERENCE
        "Section 7.6 of IEEE 1284-2000.
        printer-make-and-model in IPP/1.1 (RFC 2911)."
        DEFVAL      { ''H }                 -- no IEEE 1284 device ID
::= { ppmPrinterEntry 3 }

ppmPrinterNumberOfPorts OBJECT-TYPE
        SYNTAX      Gauge32
        MAX-ACCESS  read-only
        STATUS      current
        DESCRIPTION
        "The number of printer ports supported on this network printer,
        i.e., the number of entries in the 'ppmPortTable' below with a
        first index of 'ppmPrinterIndex', or zero if no printer ports
        are currently configured."
        DEFVAL      { 0 }                   -- no printer ports configured
::= { ppmPrinterEntry 4 }

ppmPrinterPreferredPortIndex OBJECT-TYPE
        SYNTAX      Integer32 (0..2147483647)
        MAX-ACCESS  read-only
        STATUS      current
        DESCRIPTION
        "The value of 'ppmPortIndex' for the preferred port for this
        printer (configured by vendor or site administrator), or zero if
        not specified.
        Compatibility Note:  The value of zero is NOT valid for
        'ppmPortIndex'.  It is an out-of-band value.
        If this object is non-zero, then installation applications
        SHOULD default to this port in their user interface dialogue."
        REFERENCE
        "document-format-default in IPP/1.1 (RFC 2911)."
        DEFVAL      { 0 }                   -- no preferred port configured
::= { ppmPrinterEntry 5 }

ppmPrinterHrDeviceIndex OBJECT-TYPE
        SYNTAX      Integer32 (0..2147483647)
        MAX-ACCESS  read-only
        STATUS      current
        DESCRIPTION
        "The value of 'hrDeviceIndex' in the IETF Host Resources MIB
        (RFC 1514/2790), or zero if not specified.  This value of
        'hrDeviceIndex' MAY be used for status queries for this printer
        if the value of 'ppmPrinterSnmpQueryEnabled' is 'true'.
        Compatibility Note:  The value of zero is NOT valid for
        'hrDeviceIndex'.  It is an out-of-band value.
        If this object is zero, then monitoring applications MUST NOT
        attempt status queries for this printer in the IETF Host
        Resources MIB (RFC 1514/2790) and/or IETF Printer MIB
        (RFC 1759/3805)."
        REFERENCE
        "hrDeviceStatus, hrPrinterStatus, hrPrinterDetectedErrorState
        in IETF Host Resources MIB (RFC 1514/2790).
        Section 2.2.13.2 'Overall Printer Status' and
        Appendix E 'Overall Printer Status Table' in IETF Printer MIB v2
        (RFC 3805)."
        DEFVAL      { 0 }                   -- no host device index
::= { ppmPrinterEntry 6 }

ppmPrinterSnmpCommunityName OBJECT-TYPE
        SYNTAX      OCTET STRING (SIZE (0..255))
        MAX-ACCESS  read-only
        STATUS      current
        DESCRIPTION
        "The SNMP read community name, an opaque binary string, for
        access to status information in IETF Host Resources MIB (RFC
        1514/2790) and IETF Printer MIB (RFC 1759/3805) for this printer
        via the value of 'ppmPrinterHrDeviceIndex' (i.e., a 'MIB view'
        of these two MIBs).
        Security Warning:  Due to the widespread availability of free
        'packet sniffers' (network traffic snooping applications) and
        SNMP packet decoders, SNMP community names no longer offer even
        weak security.  This object SHOULD only be used to support 'MIB
        views'.  Implementations SHOULD use SNMPv3 security to protect
        network resources from unauthorized monitoring.
        If this object is empty, then the SNMP read community name for
        this printer (if any) SHOULD default to 'public' in US-ASCII."
        REFERENCE
        "snmpCommunityName in IETF SNMP Community MIB (RFC 3584)."
        DEFVAL      { ''H }                 -- no SNMP read community name
::= { ppmPrinterEntry 7 }

ppmPrinterSnmpQueryEnabled OBJECT-TYPE
        SYNTAX      TruthValue
        MAX-ACCESS  read-only
        STATUS      current
        DESCRIPTION
        "The status query mode for this printer, for queries by
        monitoring applications in the IETF Host Resources MIB
        (RFC 1514/2790) and/or IETF Printer MIB (RFC 1759/3805).
        If this object is 'true', then monitoring applications MAY
        attempt status queries for this printer in the IETF Host
        Resources MIB and/or IETF Printer MIB.
        If this object is 'false', then monitoring applications MUST
        NOT attempt status queries for this printer in the IETF Host
        Resources MIB and/or IETF Printer MIB."
        REFERENCE
        "ppmPrinterSnmpCommunityName."
        DEFVAL      { false }               -- SNMP status queries disabled
::= { ppmPrinterEntry 8 }

ppmPortEnabled OBJECT-TYPE
        SYNTAX      TruthValue
        MAX-ACCESS  read-only
        STATUS      current
        DESCRIPTION
        "The current administrative configuration mode for this port.
        If this object is 'false', then applications MUST NOT attempt
        installation of this port and SHOULD NOT attempt print job
        submission to this port.
        If this object is 'true', then the port is currently enabled.
        If this object is 'false', then the port is currently disabled."
        REFERENCE
        "ppmPortProtocolType and ppmPortHrDeviceIndex."
        DEFVAL      { false }               -- port disabled
::= { ppmPortEntry 2 }

ppmPortName OBJECT-TYPE
        SYNTAX      SnmpAdminString (SIZE (0..127))
        MAX-ACCESS  read-only
        STATUS      current
        DESCRIPTION
        "A user friendly name for this port that may be used to
        facilitate user selection of a port on a multi-port network
        system, in the locale specified by 'ppmGeneralNaturalLanguage'.
        This port name may contain non-ASCII characters that are NOT
        allowed in a URI (RFC 3986) without percent-encoding.
        The value of this object SHOULD be unique across all ports on
        this network system and SHOULD be meaningful to end users
        (e.g., 'PrinterXYZ-LPR-Duplex').
        The value of this object SHOULD be set by an out-of-band method
        (e.g., local console) during installation (by the vendor or site
        administrator) and SHOULD NOT be subsequently modified, so that
        the value can be used as a static key for access to the port.
        The charset of this text string object is UTF-8 (RFC 3629), in
        order to support names that cannot be represented in US-ASCII."
        REFERENCE
        "prtChannelInformation in IETF Printer MIB v2 (RFC 3805)."
        DEFVAL      { ''H }                 -- port name not specified
::= { ppmPortEntry 3 }

ppmPortServiceNameOrURI OBJECT-TYPE
        SYNTAX      SnmpAdminString (SIZE (0..255))
        MAX-ACCESS  read-only
        STATUS      current
        DESCRIPTION
        "The service name or URI for this port, specified in UTF-8 (RFC
        3629), in the locale specified by 'ppmGeneralNaturalLanguage'.
        The service name is typically a queue name.
        Compatibility Note:  At the time of publication of this MIB,
        the Microsoft tools do not support LPR queue names longer than
        32 characters.  Network administrators SHOULD NOT assign longer
        LPR queue names, to prevent interworking problems.
        Compatibility Note:  At the time of publication of this MIB,
        IETF URI Generic Syntax (RFC 3986) requires that all non-ASCII
        characters be percent-encoded, while IETF Internationalized
        Resource Identifiers (RFC 3987) permits native UTF-8 resource
        identifiers and supplies mappings to and from standard URI.
        In order to support current use of IRI and possible future
        evolution of URI (in a successor to RFC 3986) to allow non-ASCII
        characters, this object has been defined with a syntax of UTF-8
        (RFC 3629).
        Examples of well-formed service URI for print protocols
        include:
        - 'lpr://foo.example.com/public-printer' (where 'public-
        printer' is the LPR queue name portion)
        and
        - 'ipp://bar.example.com/printer/fox'
        If this object is non-empty, then it SHOULD NOT conflict with a
        the default (e.g., IANA-registered) or explicit transport target
        port specified in 'ppmPortProtocolTargetPort'.  In case of
        conflict, the URI value in 'ppmPortServiceNameOrURI' is
        authoritative (e.g., 'ipp://example.com:631/~smith/printer').
        If this object is empty and 'ppmPortProtocolType' is
        'chLPDServer(8)', the LPR queue name MUST default to 'LPR'."
        REFERENCE
        "IETF Line Printer Daemon Protocol (RFC 1179).
        'lpr:' URL scheme in IANA-registered SLP Printer Schema at
        http://www.iana.org/assignments/svrloc-templates/
        printer-uri in LDAP Printer Schema (RFC 3712).
        IPP/1.1: IPP URL Scheme (RFC 3510).
        printer-uri-supported in IPP/1.1 (RFC 2911)."
        DEFVAL      { ''H }                 -- no service name or URI
::= { ppmPortEntry 4 }

ppmPortProtocolType OBJECT-TYPE
        SYNTAX      Integer32 (0..2147483647)
        MAX-ACCESS  read-only
        STATUS      current
        DESCRIPTION
        "The protocol type of this printer port, specified as a value
        from 'PrtChannelTypeTC' in the IANA Printer MIB (e.g.,
        'chLPDServer(8)' for LPR (RFC 1179) or 'chPort9100(11)' for
        Raw), or zero if not specified.
        Compatibility Note:  The value of zero is NOT registered in the
        IANA Printer MIB.  It is an out-of-band value.  Thus the syntax
        of this object is NOT specified as 'PrtChannelTypeTC'.
        Systems that do NOT implement IETF Printer MIB v2 (RFC 3805)
        SHOULD use 'chPort9100(11)' for Raw printing (with an alternate
        port in 'ppmPortProtocolTargetPort', if necessary), because
        'chPortTCP(37)' and 'chBidirPortTCP(38)' are NOT defined in
        IETF Printer MIB v1 (RFC 1759).
        Systems that do implement the IETF Printer MIB v2 (RFC 3805)
        MAY instead use 'chPortTCP(37)' or 'chBidirPortTCP(38)' for Raw
        printing, because 'chPort9100(11)' is DEPRECATED in IETF
        Printer MIB v2.
        Systems that implement any version of the IETF Printer MIB
        (RFC 1759/3805) SHOULD use the same value of protocol type for
        this port in the 'prtChannelTable', so monitoring applications
        MAY search for more channel information and status."
        REFERENCE
        "PrtChannelTypeTC in IANA Printer MIB (RFC 3805 and
        http://www.iana.org/assignments/ianaprinter-mib).
        prtChannelType in IETF Printer MIB (RFC 1759/3805)."
        DEFVAL      { 0 }                   -- protocol type not specified
::= { ppmPortEntry 5 }

ppmPortProtocolTargetPort OBJECT-TYPE
        SYNTAX      Integer32 (0..65535)
        MAX-ACCESS  read-only
        STATUS      current
        DESCRIPTION
        "The transport (TCP, UDP, etc.) target port number for this
        protocol, i.e., an alternate port from the protocol default, or
        zero if not specified (use protocol default).  This object MAY
        be used for any print protocol (from the Internet, NetWare,
        AppleTalk, or other protocol suite).
        If this object is zero, then the actual target port number is
        the default port for the specified 'ppmPortProtocolType' (e.g.,
        'chPort9100(11)' uses '9100').
        If this object is non-zero, then it SHOULD NOT conflict with the
        default (e.g., IANA-registered) target port implied by the value
        of 'ppmPortProtocolType' or the explicit transport target port
        specified in 'ppmPortServiceNameOrURI'.  In case of conflict,
        the URI value in 'ppmPortServiceNameOrURI' is authoritative
        (e.g., 'ipp://example.com:631/~smith/printer').
        If 'ppmPortProtocolType' is 'chLPDServer(8)', then this object
        MUST be ignored (because LPR target port is fixed at '515')."
        REFERENCE
        "IETF Line Printer Daemon Protocol (RFC 1179)."
        DEFVAL      { 0 }                   -- target port not specified
::= { ppmPortEntry 6 }

ppmPortProtocolAltSourceEnabled OBJECT-TYPE
        SYNTAX      TruthValue
        MAX-ACCESS  read-only
        STATUS      current
        DESCRIPTION
        "The alternate transport source port mode for this protocol.
        If this object is 'true', then transport source ports outside
        the standard range MAY be used (e.g., LPR source port standard
        range is defined in RFC 1179 to be '721' to '731', inclusive).
        If this object is 'false', then transport source ports outside
        the standard range MUST NOT be used (to avoid protocol
        errors)."
        REFERENCE
        "IETF Line Printer Daemon Protocol (RFC 1179)."
        DEFVAL      { false }               -- alt source ports disabled
::= { ppmPortEntry 7 }

ppmPortPrtChannelIndex OBJECT-TYPE
        SYNTAX      Integer32 (0..65535)
        MAX-ACCESS  read-only
        STATUS      current
        DESCRIPTION
        "The value of 'prtChannelIndex' in IETF Printer MIB
        (RFC 1759/3805) that corresponds to this printer port, or zero
        if not specified.
        Compatibility Note:  The value of zero is NOT valid for
        'prtChannelIndex'.  It is an out-of-band value.
        Systems that implement any version of the IETF Printer MIB
        (RFC 1759/3805) SHOULD correctly implement this object, so
        monitoring applications MAY search for print channel information
        and status.
        If this object is zero, then monitoring applications MUST NOT
        attempt print channel status queries for this printer port."
        REFERENCE
        "prtChannelIndex, prtChannelIfIndex, prtChannelState, and
        prtChannelStatus in IETF Printer MIB (RFC 1759/3805)."
        DEFVAL      { 0 }                   -- no print channel index
::= { ppmPortEntry 8 }

ppmPortLprByteCountEnabled OBJECT-TYPE
        SYNTAX      TruthValue
        MAX-ACCESS  read-only
        STATUS      current
        DESCRIPTION
        "The current LPR byte counting mode for this port if applicable.
        If the value of 'ppmPortProtocolType' is NOT 'chLPDServer(8)',
        then monitoring applications MUST ignore the value of this
        object.
        If this object is 'true', then LPR byte counting is enabled.
        If this object is 'false', then LPR byte counting is disabled."
        REFERENCE
        "IETF Line Printer Daemon Protocol (RFC 1179)."
        DEFVAL      { false }               -- LPR byte counting disabled
::= { ppmPortEntry 9 }

speed-energy-usage OBJECT-TYPE
   SYNTAX     INTEGER { 
                      eFasterFirstPage(1),
                      eSaveEnergy(2),
                      eSaveMostEnergy(3),
                      eSaveMoreEnergy(4)
               }
   ACCESS     read-write 
   STATUS      optional
   DESCRIPTION "Option to keep the fuser in a pre-warmed state to speed up
               first page out." 
   ::={ settings-system 50 } 

enable-engine-early-warmup OBJECT-TYPE
   SYNTAX     INTEGER { 
                      eDisable(1),
                      eEnable(2)
               }
   ACCESS     read-write 
   STATUS      optional
   DESCRIPTION "This PML object is used by HP SW to enable/disable the printer
               to send the signal of warm-up process early to engine. The
               effect of warming up early will reduce the First Page Out
               time." 
   ::= { settings-system 101 } 

total-engine-page-count OBJECT-TYPE
   SYNTAX     INTEGER 
   ACCESS     read-write 
   STATUS      optional
   DESCRIPTION "Total number of pages printed by the device. POS indicates if
               the total engine page count is kept in NVRAM, and the maximum
               supported value before the page count rolls over to zero." 
   ::= { status-prt-eng 5 }

fax-print-page-count OBJECT-TYPE
   SYNTAX     INTEGER 
   ACCESS     read-write 
   STATUS      optional
   DESCRIPTION "This object tracks the page count for the pages sent to the
               print engine for fax jobs. In order to write this object
               SERVICE-PASSWORD must be set correctly." 
   ::= { settings-fax-proc-sub 32 }

total-mono-page-count OBJECT-TYPE
   SYNTAX     INTEGER 
   ACCESS     read-only 
   STATUS      optional
   DESCRIPTION "Total number of black pages printed by the device." 
   ::= { status-prt-eng 6 } 

END
