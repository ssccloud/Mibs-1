--
-- HUAWEI-STORAGE-HARDWARE-MIB.mib
-- MIB generated by MG-SOFT Visual MIB Builder Version 3.0 Build 253
-- Sunday, June 12, 2016 at 19:31:04
--

--  HUAWEI-STORAGE-HARDWARE-MIB.mib
-- MIB generated by MG-SOFT Visual MIB Builder Version 4.0 Build 347
-- Friday, October 17, 2014 at 18:50:14
-- 

	HUAWEI-STORAGE-HARDWARE-MIB DEFINITIONS ::= BEGIN
 
		IMPORTS
			OBJECT-GROUP, MODULE-COMPLIANCE			
				FROM SNMPv2-CONF			
			enterprises, Integer32, Unsigned32, Counter64, 
			OBJECT-TYPE, MODULE-IDENTITY			
				FROM SNMPv2-SMI			
			TEXTUAL-CONVENTION			
				FROM SNMPv2-TC;
	
	
		hwStorage MODULE-IDENTITY 
			LAST-UPDATED "201008111239Z"		-- August 11, 2010 at 12:39 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"Description."
			REVISION "201404061354Z"		-- April 06, 2014 at 13:54 GMT
			DESCRIPTION
				" "
			::= { huaweistorage 4 }
		
	
--
-- Textual conventions
--
	
--  August 11, 2010 at 12:39 GMT
-- April 06, 2014 at 13:54 GMT
-- 
-- Textual conventions
-- 
--  August 11, 2010 at 12:39 GMT
-- April 06, 2014 at 13:54 GMT
-- 
-- Textual conventions
-- 
		NodeCodeString ::= TEXTUAL-CONVENTION
			DISPLAY-HINT 
				"255a"
			STATUS current
			DESCRIPTION 
				"characters in length."
			SYNTAX OCTET STRING (SIZE (15..17))
			
	
--
-- Node definitions
--
	
--  Node definitions
-- 
		-- 1.3.6.1.4.1.34774
		huaweistorage OBJECT IDENTIFIER ::= { enterprises 34774 }
		
		-- 1.3.6.1.4.1.34774.4.1
		hwISM OBJECT IDENTIFIER ::= { hwStorage 1 }
		
		-- 1.3.6.1.4.1.34774.4.1.23
		hwStorageDevice OBJECT IDENTIFIER ::= { hwISM 23 }
		
		-- 1.3.6.1.4.1.34774.4.1.23.5
		hwHardwareInfo OBJECT IDENTIFIER ::= { hwStorageDevice 5 }
		
		-- 1.3.6.1.4.1.34774.4.1.23.5.1
		hwInfoDiskTable OBJECT-TYPE
			SYNTAX SEQUENCE OF HwInfoDiskEntry
			MAX-ACCESS not-accessible
			STATUS current
			DESCRIPTION
				" "
			::= { hwHardwareInfo 1 }
		
		-- 1.3.6.1.4.1.34774.4.1.23.5.1.1
		hwInfoDiskEntry OBJECT-TYPE
			SYNTAX HwInfoDiskEntry
			MAX-ACCESS not-accessible
			STATUS current
			DESCRIPTION
				" "
			INDEX { hwInfoDiskID }
			::= { hwInfoDiskTable 1 }
		
		HwInfoDiskEntry ::=
			SEQUENCE { 
				hwInfoDiskID
					OCTET STRING,
				hwInfoDiskHealthStatus
					Unsigned32,
				hwInfoDiskRunningStatus
					Unsigned32,
				hwInfoDiskLocation
					OCTET STRING,
				hwInfoDiskType
					Unsigned32,
				hwInfoDiskCapacity
					Counter64,
				hwInfoDiskRole
					Unsigned32,
				hwInfoDiskSpeed
					Unsigned32,
				hwInfoDiskInterfaceBandwidth
					Unsigned32,
				hwInfoDiskSectorSize
					Unsigned32,
				hwInfoDiskTemperature
					Integer32,
				hwInfoDiskModel
					OCTET STRING,
				hwInfoDiskFirmwareVersion
					OCTET STRING,
				hwInfoDiskManufacturer
					OCTET STRING,
				hwInfoDiskSerialNumber
					OCTET STRING,
				hwInfoDiskLightStatus
					Unsigned32,
				hwInfoDiskDiskDomainID
					OCTET STRING,
				hwInfoDiskDiskDomainName
					OCTET STRING,
				hwInfoDiskDiskDomainTierID
					OCTET STRING,
				hwInfoDiskCofferDisk
					Unsigned32,
				hwInfoDiskRunTime
					Unsigned32,
				hwInfoDiskProgress
					Unsigned32,
				hwInfoDiskBarCode
					OCTET STRING,
				hwInfoDiskCapacityUsage
					Unsigned32,
				hwInfoDiskHealthMark
					Unsigned32,
                hwInfoDiskElectronicLabel
                    OCTET STRING
			 }

		-- 1.3.6.1.4.1.34774.4.1.23.5.1.1.1
		hwInfoDiskID OBJECT-TYPE
			SYNTAX OCTET STRING
			MAX-ACCESS read-only
			STATUS current
			DESCRIPTION
				"  "
			::= { hwInfoDiskEntry 1 }
		
		-- 1.3.6.1.4.1.34774.4.1.23.5.1.1.2
		hwInfoDiskHealthStatus OBJECT-TYPE
			SYNTAX Unsigned32
			MAX-ACCESS read-only
			STATUS current
			DESCRIPTION
				"  "
			::= { hwInfoDiskEntry 2 }
		
		-- 1.3.6.1.4.1.34774.4.1.23.5.1.1.3
		hwInfoDiskRunningStatus OBJECT-TYPE
			SYNTAX Unsigned32
			MAX-ACCESS read-only
			STATUS current
			DESCRIPTION
				"  "
			::= { hwInfoDiskEntry 3 }
		
		-- 1.3.6.1.4.1.34774.4.1.23.5.1.1.4
		hwInfoDiskLocation OBJECT-TYPE
			SYNTAX OCTET STRING
			MAX-ACCESS read-only
			STATUS current
			DESCRIPTION
				"  "
			::= { hwInfoDiskEntry 4 }
		
		-- 1.3.6.1.4.1.34774.4.1.23.5.1.1.5
		hwInfoDiskType OBJECT-TYPE
			SYNTAX Unsigned32
			MAX-ACCESS read-only
			STATUS current
			DESCRIPTION
				"  "
			::= { hwInfoDiskEntry 5 }
		
		-- 1.3.6.1.4.1.34774.4.1.23.5.1.1.6
		hwInfoDiskCapacity OBJECT-TYPE
			SYNTAX Counter64
			MAX-ACCESS read-only
			STATUS current
			DESCRIPTION
				"  "
			::= { hwInfoDiskEntry 6 }
		
		-- 1.3.6.1.4.1.34774.4.1.23.5.1.1.7
		hwInfoDiskRole OBJECT-TYPE
			SYNTAX Unsigned32
			MAX-ACCESS read-only
			STATUS current
			DESCRIPTION
				" "
			::= { hwInfoDiskEntry 7 }
		
		-- 1.3.6.1.4.1.34774.4.1.23.5.1.1.8
		hwInfoDiskSpeed OBJECT-TYPE
			SYNTAX Unsigned32
			MAX-ACCESS read-only
			STATUS current
			DESCRIPTION
				"  "
			::= { hwInfoDiskEntry 8 }
		
		-- 1.3.6.1.4.1.34774.4.1.23.5.1.1.9
		hwInfoDiskInterfaceBandwidth OBJECT-TYPE
			SYNTAX Unsigned32
			MAX-ACCESS read-only
			STATUS current
			DESCRIPTION
				"  "
			::= { hwInfoDiskEntry 9 }
		
		-- 1.3.6.1.4.1.34774.4.1.23.5.1.1.10
		hwInfoDiskSectorSize OBJECT-TYPE
			SYNTAX Unsigned32
			MAX-ACCESS read-only
			STATUS current
			DESCRIPTION
				"  "
			::= { hwInfoDiskEntry 10 }
		
		-- 1.3.6.1.4.1.34774.4.1.23.5.1.1.11
		hwInfoDiskTemperature OBJECT-TYPE
			SYNTAX Integer32
			MAX-ACCESS read-only
			STATUS current
			DESCRIPTION
				"  "
			::= { hwInfoDiskEntry 11 }
		
		-- 1.3.6.1.4.1.34774.4.1.23.5.1.1.12
		hwInfoDiskModel OBJECT-TYPE
			SYNTAX OCTET STRING
			MAX-ACCESS read-only
			STATUS current
			DESCRIPTION
				"  "
			::= { hwInfoDiskEntry 12 }
		
		-- 1.3.6.1.4.1.34774.4.1.23.5.1.1.13
		hwInfoDiskFirmwareVersion OBJECT-TYPE
			SYNTAX OCTET STRING
			MAX-ACCESS read-only
			STATUS current
			DESCRIPTION
				"  "
			::= { hwInfoDiskEntry 13 }
		
		-- 1.3.6.1.4.1.34774.4.1.23.5.1.1.14
		hwInfoDiskManufacturer OBJECT-TYPE
			SYNTAX OCTET STRING
			MAX-ACCESS read-only
			STATUS current
			DESCRIPTION
				"  "
			::= { hwInfoDiskEntry 14 }
		
		-- 1.3.6.1.4.1.34774.4.1.23.5.1.1.15
		hwInfoDiskSerialNumber OBJECT-TYPE
			SYNTAX OCTET STRING
			MAX-ACCESS read-only
			STATUS current
			DESCRIPTION
				"  "
			::= { hwInfoDiskEntry 15 }
		
		-- 1.3.6.1.4.1.34774.4.1.23.5.1.1.16
		hwInfoDiskLightStatus OBJECT-TYPE
			SYNTAX Unsigned32
			MAX-ACCESS read-only
			STATUS current
			DESCRIPTION
				"  "
			::= { hwInfoDiskEntry 16 }
		
		-- 1.3.6.1.4.1.34774.4.1.23.5.1.1.17
		hwInfoDiskDiskDomainID OBJECT-TYPE
			SYNTAX OCTET STRING
			MAX-ACCESS read-only
			STATUS current
			DESCRIPTION
				" "
			::= { hwInfoDiskEntry 17 }
		
		-- 1.3.6.1.4.1.34774.4.1.23.5.1.1.18
		hwInfoDiskDiskDomainName OBJECT-TYPE
			SYNTAX OCTET STRING
			MAX-ACCESS read-only
			STATUS current
			DESCRIPTION
				"  "
			::= { hwInfoDiskEntry 18 }
		
		-- 1.3.6.1.4.1.34774.4.1.23.5.1.1.19
		hwInfoDiskDiskDomainTierID OBJECT-TYPE
			SYNTAX OCTET STRING
			MAX-ACCESS read-only
			STATUS current
			DESCRIPTION
				"  "
			::= { hwInfoDiskEntry 19 }
		
		-- 1.3.6.1.4.1.34774.4.1.23.5.1.1.20
		hwInfoDiskCofferDisk OBJECT-TYPE
			SYNTAX Unsigned32
			MAX-ACCESS read-only
			STATUS current
			DESCRIPTION
				"  "
			::= { hwInfoDiskEntry 20 }
		
		-- 1.3.6.1.4.1.34774.4.1.23.5.1.1.21
		hwInfoDiskRunTime OBJECT-TYPE
			SYNTAX Unsigned32
			MAX-ACCESS read-only
			STATUS current
			DESCRIPTION
				"  "
			::= { hwInfoDiskEntry 21 }
		
		-- 1.3.6.1.4.1.34774.4.1.23.5.1.1.22
		hwInfoDiskProgress OBJECT-TYPE
			SYNTAX Unsigned32
			MAX-ACCESS read-only
			STATUS current
			DESCRIPTION
				"  "
			::= { hwInfoDiskEntry 22 }
		
		-- 1.3.6.1.4.1.34774.4.1.23.5.1.1.23
		hwInfoDiskBarCode OBJECT-TYPE
			SYNTAX OCTET STRING
			MAX-ACCESS read-only
			STATUS current
			DESCRIPTION
				"  "
			::= { hwInfoDiskEntry 23 }
		
		-- 1.3.6.1.4.1.34774.4.1.23.5.1.1.24
		hwInfoDiskCapacityUsage OBJECT-TYPE
			SYNTAX Unsigned32
			MAX-ACCESS read-only
			STATUS current
			DESCRIPTION
				"  "
			::= { hwInfoDiskEntry 24 }
		
		-- 1.3.6.1.4.1.34774.4.1.23.5.1.1.25
		hwInfoDiskHealthMark OBJECT-TYPE
			SYNTAX Unsigned32
			MAX-ACCESS read-only
			STATUS current
			DESCRIPTION
				"  "
			::= { hwInfoDiskEntry 25 }
            
        -- 1.3.6.1.4.1.34774.4.1.23.5.1.1.26
		hwInfoDiskElectronicLabel OBJECT-TYPE
			SYNTAX OCTET STRING
			MAX-ACCESS read-only
			STATUS current
			DESCRIPTION
				"  "
			::= { hwInfoDiskEntry 26 }
		
		-- 1.3.6.1.4.1.34774.4.1.23.5.2
		hwInfoControllerTable OBJECT-TYPE
			SYNTAX SEQUENCE OF HwInfoControllerEntry
			MAX-ACCESS not-accessible
			STATUS current
			DESCRIPTION
				" "
			::= { hwHardwareInfo 2 }
		
		-- 1.3.6.1.4.1.34774.4.1.23.5.2.1
		hwInfoControllerEntry OBJECT-TYPE
			SYNTAX HwInfoControllerEntry
			MAX-ACCESS not-accessible
			STATUS current
			DESCRIPTION
				" "
			INDEX { hwInfoControllerID }
			::= { hwInfoControllerTable 1 }
		
		HwInfoControllerEntry ::=
			SEQUENCE { 
				hwInfoControllerID
					OCTET STRING,
				hwInfoControllerHealthStatus
					Unsigned32,
				hwInfoControllerRunningStatus
					Unsigned32,
				hwInfoControllerCPU
					OCTET STRING,
				hwInfoControllerLocation
					OCTET STRING,
				hwInfoControllerRole
					Unsigned32,
				hwInfoControllerCacheCapacity
					Unsigned32,
				hwInfoControllerCPUUsage
					Unsigned32,
				hwInfoControllerMemoryUsage
					Unsigned32,
				hwInfoControllerVoltage
					Unsigned32,
				hwInfoControllerSoftwareVersion
					OCTET STRING,
				hwInfoControllerPCBVersion
					OCTET STRING,
				hwInfoControllerSESVersion
					OCTET STRING,
				hwInfoControllerBMCVersion
					OCTET STRING,
				hwInfoControllerLogicVersion
					OCTET STRING,
				hwInfoControllerBIOSVersion
					OCTET STRING,
				hwInfoControllerElectronicLabel
					OCTET STRING
			 }

		-- 1.3.6.1.4.1.34774.4.1.23.5.2.1.1
		hwInfoControllerID OBJECT-TYPE
			SYNTAX OCTET STRING
			MAX-ACCESS read-only
			STATUS current
			DESCRIPTION
				"  "
			::= { hwInfoControllerEntry 1 }
		
		-- 1.3.6.1.4.1.34774.4.1.23.5.2.1.2
		hwInfoControllerHealthStatus OBJECT-TYPE
			SYNTAX Unsigned32
			MAX-ACCESS read-only
			STATUS current
			DESCRIPTION
				"  "
			::= { hwInfoControllerEntry 2 }
		
		-- 1.3.6.1.4.1.34774.4.1.23.5.2.1.3
		hwInfoControllerRunningStatus OBJECT-TYPE
			SYNTAX Unsigned32
			MAX-ACCESS read-only
			STATUS current
			DESCRIPTION
				"  "
			::= { hwInfoControllerEntry 3 }
		
		-- 1.3.6.1.4.1.34774.4.1.23.5.2.1.4
		hwInfoControllerCPU OBJECT-TYPE
			SYNTAX OCTET STRING
			MAX-ACCESS read-only
			STATUS current
			DESCRIPTION
				"  "
			::= { hwInfoControllerEntry 4 }
		
		-- 1.3.6.1.4.1.34774.4.1.23.5.2.1.5
		hwInfoControllerLocation OBJECT-TYPE
			SYNTAX OCTET STRING
			MAX-ACCESS read-only
			STATUS current
			DESCRIPTION
				"  "
			::= { hwInfoControllerEntry 5 }
		
		-- 1.3.6.1.4.1.34774.4.1.23.5.2.1.6
		hwInfoControllerRole OBJECT-TYPE
			SYNTAX Unsigned32
			MAX-ACCESS read-only
			STATUS current
			DESCRIPTION
				"  "
			::= { hwInfoControllerEntry 6 }
		
		-- 1.3.6.1.4.1.34774.4.1.23.5.2.1.7
		hwInfoControllerCacheCapacity OBJECT-TYPE
			SYNTAX Unsigned32
			MAX-ACCESS read-only
			STATUS current
			DESCRIPTION
				"  "
			::= { hwInfoControllerEntry 7 }
		
		-- 1.3.6.1.4.1.34774.4.1.23.5.2.1.8
		hwInfoControllerCPUUsage OBJECT-TYPE
			SYNTAX Unsigned32
			MAX-ACCESS read-only
			STATUS current
			DESCRIPTION
				"  "
			::= { hwInfoControllerEntry 8 }
		
		-- 1.3.6.1.4.1.34774.4.1.23.5.2.1.9
		hwInfoControllerMemoryUsage OBJECT-TYPE
			SYNTAX Unsigned32
			MAX-ACCESS read-only
			STATUS current
			DESCRIPTION
				"  "
			::= { hwInfoControllerEntry 9 }
		
		-- 1.3.6.1.4.1.34774.4.1.23.5.2.1.10
		hwInfoControllerVoltage OBJECT-TYPE
			SYNTAX Unsigned32
			MAX-ACCESS read-only
			STATUS current
			DESCRIPTION
				"  "
			::= { hwInfoControllerEntry 10 }
		
		-- 1.3.6.1.4.1.34774.4.1.23.5.2.1.11
		hwInfoControllerSoftwareVersion OBJECT-TYPE
			SYNTAX OCTET STRING
			MAX-ACCESS read-only
			STATUS current
			DESCRIPTION
				"  "
			::= { hwInfoControllerEntry 11 }
		
		-- 1.3.6.1.4.1.34774.4.1.23.5.2.1.12
		hwInfoControllerPCBVersion OBJECT-TYPE
			SYNTAX OCTET STRING
			MAX-ACCESS read-only
			STATUS current
			DESCRIPTION
				"  "
			::= { hwInfoControllerEntry 12 }
		
		-- 1.3.6.1.4.1.34774.4.1.23.5.2.1.13
		hwInfoControllerSESVersion OBJECT-TYPE
			SYNTAX OCTET STRING
			MAX-ACCESS read-only
			STATUS current
			DESCRIPTION
				"  "
			::= { hwInfoControllerEntry 13 }
		
		-- 1.3.6.1.4.1.34774.4.1.23.5.2.1.14
		hwInfoControllerBMCVersion OBJECT-TYPE
			SYNTAX OCTET STRING
			MAX-ACCESS read-only
			STATUS current
			DESCRIPTION
				"  "
			::= { hwInfoControllerEntry 14 }
		
		-- 1.3.6.1.4.1.34774.4.1.23.5.2.1.15
		hwInfoControllerLogicVersion OBJECT-TYPE
			SYNTAX OCTET STRING
			MAX-ACCESS read-only
			STATUS current
			DESCRIPTION
				"  "
			::= { hwInfoControllerEntry 15 }
		
		-- 1.3.6.1.4.1.34774.4.1.23.5.2.1.16
		hwInfoControllerBIOSVersion OBJECT-TYPE
			SYNTAX OCTET STRING
			MAX-ACCESS read-only
			STATUS current
			DESCRIPTION
				"  "
			::= { hwInfoControllerEntry 16 }
		
		-- 1.3.6.1.4.1.34774.4.1.23.5.2.1.17
		hwInfoControllerElectronicLabel OBJECT-TYPE
			SYNTAX OCTET STRING
			MAX-ACCESS read-only
			STATUS current
			DESCRIPTION
				"  "
			::= { hwInfoControllerEntry 17 }
		
		-- 1.3.6.1.4.1.34774.4.1.23.5.3
		hwInfoPowerTable OBJECT-TYPE
			SYNTAX SEQUENCE OF HwInfoPowerEntry
			MAX-ACCESS not-accessible
			STATUS current
			DESCRIPTION
				" "
			::= { hwHardwareInfo 3 }
		
		-- 1.3.6.1.4.1.34774.4.1.23.5.3.1
		hwInfoPowerEntry OBJECT-TYPE
			SYNTAX HwInfoPowerEntry
			MAX-ACCESS not-accessible
			STATUS current
			DESCRIPTION
				"  "
			INDEX { hwInfoPowerID }
			::= { hwInfoPowerTable 1 }
		
		HwInfoPowerEntry ::=
			SEQUENCE { 
				hwInfoPowerID
					OCTET STRING,
				hwInfoPowerLocation
					OCTET STRING,
				hwInfoPowerHealthStatus
					Unsigned32,
				hwInfoPowerRunningStatus
					Unsigned32,
				hwInfoPowerType
					Unsigned32,
				hwInfoPowerManufacturer
					OCTET STRING,
				hwInfoPowerModle
					OCTET STRING,
				hwInfoPowerVersion
					OCTET STRING,
				hwInfoPowerProduceDate
					OCTET STRING,
				hwInfoPowerSerialNumber
					OCTET STRING
			 }

		-- 1.3.6.1.4.1.34774.4.1.23.5.3.1.1
		hwInfoPowerID OBJECT-TYPE
			SYNTAX OCTET STRING
			MAX-ACCESS read-only
			STATUS current
			DESCRIPTION
				"  "
			::= { hwInfoPowerEntry 1 }
		
		-- 1.3.6.1.4.1.34774.4.1.23.5.3.1.2
		hwInfoPowerLocation OBJECT-TYPE
			SYNTAX OCTET STRING
			MAX-ACCESS read-only
			STATUS current
			DESCRIPTION
				"  "
			::= { hwInfoPowerEntry 2 }
		
		-- 1.3.6.1.4.1.34774.4.1.23.5.3.1.3
		hwInfoPowerHealthStatus OBJECT-TYPE
			SYNTAX Unsigned32
			MAX-ACCESS read-only
			STATUS current
			DESCRIPTION
				"  "
			::= { hwInfoPowerEntry 3 }
		
		-- 1.3.6.1.4.1.34774.4.1.23.5.3.1.4
		hwInfoPowerRunningStatus OBJECT-TYPE
			SYNTAX Unsigned32
			MAX-ACCESS read-only
			STATUS current
			DESCRIPTION
				"  "
			::= { hwInfoPowerEntry 4 }
		
		-- 1.3.6.1.4.1.34774.4.1.23.5.3.1.5
		hwInfoPowerType OBJECT-TYPE
			SYNTAX Unsigned32
			MAX-ACCESS read-only
			STATUS current
			DESCRIPTION
				"  "
			::= { hwInfoPowerEntry 5 }
		
		-- 1.3.6.1.4.1.34774.4.1.23.5.3.1.6
		hwInfoPowerManufacturer OBJECT-TYPE
			SYNTAX OCTET STRING
			MAX-ACCESS read-only
			STATUS current
			DESCRIPTION
				"  "
			::= { hwInfoPowerEntry 6 }
		
		-- 1.3.6.1.4.1.34774.4.1.23.5.3.1.7
		hwInfoPowerModle OBJECT-TYPE
			SYNTAX OCTET STRING
			MAX-ACCESS read-only
			STATUS current
			DESCRIPTION
				"  "
			::= { hwInfoPowerEntry 7 }
		
		-- 1.3.6.1.4.1.34774.4.1.23.5.3.1.8
		hwInfoPowerVersion OBJECT-TYPE
			SYNTAX OCTET STRING
			MAX-ACCESS read-only
			STATUS current
			DESCRIPTION
				"  "
			::= { hwInfoPowerEntry 8 }
		
		-- 1.3.6.1.4.1.34774.4.1.23.5.3.1.9
		hwInfoPowerProduceDate OBJECT-TYPE
			SYNTAX OCTET STRING
			MAX-ACCESS read-only
			STATUS current
			DESCRIPTION
				"  "
			::= { hwInfoPowerEntry 9 }
		
		-- 1.3.6.1.4.1.34774.4.1.23.5.3.1.10
		hwInfoPowerSerialNumber OBJECT-TYPE
			SYNTAX OCTET STRING
			MAX-ACCESS read-only
			STATUS current
			DESCRIPTION
				"  "
			::= { hwInfoPowerEntry 10 }
		
		-- 1.3.6.1.4.1.34774.4.1.23.5.4
		hwInfoFanTable OBJECT-TYPE
			SYNTAX SEQUENCE OF HwInfoFanEntry
			MAX-ACCESS not-accessible
			STATUS current
			DESCRIPTION
				" "
			::= { hwHardwareInfo 4 }
		
		-- 1.3.6.1.4.1.34774.4.1.23.5.4.1
		hwInfoFanEntry OBJECT-TYPE
			SYNTAX HwInfoFanEntry
			MAX-ACCESS not-accessible
			STATUS current
			DESCRIPTION
				" "
			INDEX { hwInfoFanID }
			::= { hwInfoFanTable 1 }
		
		HwInfoFanEntry ::=
			SEQUENCE { 
				hwInfoFanID
					OCTET STRING,
				hwInfoFanLocation
					OCTET STRING,
				hwInfoFanHealthStatus
					Unsigned32,
				hwInfoFanRunningStatus
					Unsigned32,
				hwInfoFanRunningLevel
					Unsigned32,
				hwInfoFanElectronicLabel
					OCTET STRING
			 }

		-- 1.3.6.1.4.1.34774.4.1.23.5.4.1.1
		hwInfoFanID OBJECT-TYPE
			SYNTAX OCTET STRING
			MAX-ACCESS read-only
			STATUS current
			DESCRIPTION
				"  "
			::= { hwInfoFanEntry 1 }
		
		-- 1.3.6.1.4.1.34774.4.1.23.5.4.1.2
		hwInfoFanLocation OBJECT-TYPE
			SYNTAX OCTET STRING
			MAX-ACCESS read-only
			STATUS current
			DESCRIPTION
				"  "
			::= { hwInfoFanEntry 2 }
		
		-- 1.3.6.1.4.1.34774.4.1.23.5.4.1.3
		hwInfoFanHealthStatus OBJECT-TYPE
			SYNTAX Unsigned32
			MAX-ACCESS read-only
			STATUS current
			DESCRIPTION
				"  "
			::= { hwInfoFanEntry 3 }
		
		-- 1.3.6.1.4.1.34774.4.1.23.5.4.1.4
		hwInfoFanRunningStatus OBJECT-TYPE
			SYNTAX Unsigned32
			MAX-ACCESS read-only
			STATUS current
			DESCRIPTION
				"  "
			::= { hwInfoFanEntry 4 }
		
		-- 1.3.6.1.4.1.34774.4.1.23.5.4.1.5
		hwInfoFanRunningLevel OBJECT-TYPE
			SYNTAX Unsigned32
			MAX-ACCESS read-only
			STATUS current
			DESCRIPTION
				"  "
			::= { hwInfoFanEntry 5 }
		
		-- 1.3.6.1.4.1.34774.4.1.23.5.4.1.6
		hwInfoFanElectronicLabel OBJECT-TYPE
			SYNTAX OCTET STRING
			MAX-ACCESS read-only
			STATUS current
			DESCRIPTION
				"  "
			::= { hwInfoFanEntry 6 }
		
		-- 1.3.6.1.4.1.34774.4.1.23.5.5
		hwInfoBBUTable OBJECT-TYPE
			SYNTAX SEQUENCE OF HwInfoBBUEntry
			MAX-ACCESS not-accessible
			STATUS current
			DESCRIPTION
				" "
			::= { hwHardwareInfo 5 }
		
		-- 1.3.6.1.4.1.34774.4.1.23.5.5.1
		hwInfoBBUEntry OBJECT-TYPE
			SYNTAX HwInfoBBUEntry
			MAX-ACCESS not-accessible
			STATUS current
			DESCRIPTION
				" "
			INDEX { hwInfoBBUID }
			::= { hwInfoBBUTable 1 }
		
		HwInfoBBUEntry ::=
			SEQUENCE { 
				hwInfoBBUID
					OCTET STRING,
				hwInfoBBULocation
					OCTET STRING,
				hwInfoBBUHealthStatus
					Unsigned32,
				hwInfoBBURunningStatus
					Unsigned32,
				hwInfoBBUType
					Unsigned32,
				hwInfoBBUCurrentVoltage
					Unsigned32,
				hwInfoBBUNumberOfDischarges
					Unsigned32,
				hwInfoBBUFirmwareVersion
					OCTET STRING,
				hwInfoBBUDeliveredOn
					OCTET STRING,
				hwInfoBBUOwningController
					OCTET STRING,
				hwInfoBBUElectronicLabel
					OCTET STRING
			 }

		-- 1.3.6.1.4.1.34774.4.1.23.5.5.1.1
		hwInfoBBUID OBJECT-TYPE
			SYNTAX OCTET STRING
			MAX-ACCESS read-only
			STATUS current
			DESCRIPTION
				"  "
			::= { hwInfoBBUEntry 1 }
		
		-- 1.3.6.1.4.1.34774.4.1.23.5.5.1.2
		hwInfoBBULocation OBJECT-TYPE
			SYNTAX OCTET STRING
			MAX-ACCESS read-only
			STATUS current
			DESCRIPTION
				"  "
			::= { hwInfoBBUEntry 2 }
		
		-- 1.3.6.1.4.1.34774.4.1.23.5.5.1.3
		hwInfoBBUHealthStatus OBJECT-TYPE
			SYNTAX Unsigned32
			MAX-ACCESS read-only
			STATUS current
			DESCRIPTION
				"  "
			::= { hwInfoBBUEntry 3 }
		
		-- 1.3.6.1.4.1.34774.4.1.23.5.5.1.4
		hwInfoBBURunningStatus OBJECT-TYPE
			SYNTAX Unsigned32
			MAX-ACCESS read-only
			STATUS current
			DESCRIPTION
				"  "
			::= { hwInfoBBUEntry 4 }
		
		-- 1.3.6.1.4.1.34774.4.1.23.5.5.1.5
		hwInfoBBUType OBJECT-TYPE
			SYNTAX Unsigned32
			MAX-ACCESS read-only
			STATUS current
			DESCRIPTION
				"  "
			::= { hwInfoBBUEntry 5 }
		
		-- 1.3.6.1.4.1.34774.4.1.23.5.5.1.6
		hwInfoBBUCurrentVoltage OBJECT-TYPE
			SYNTAX Unsigned32
			MAX-ACCESS read-only
			STATUS current
			DESCRIPTION
				"  "
			::= { hwInfoBBUEntry 6 }
		
		-- 1.3.6.1.4.1.34774.4.1.23.5.5.1.7
		hwInfoBBUNumberOfDischarges OBJECT-TYPE
			SYNTAX Unsigned32
			MAX-ACCESS read-only
			STATUS current
			DESCRIPTION
				"  "
			::= { hwInfoBBUEntry 7 }
		
		-- 1.3.6.1.4.1.34774.4.1.23.5.5.1.8
		hwInfoBBUFirmwareVersion OBJECT-TYPE
			SYNTAX OCTET STRING
			MAX-ACCESS read-only
			STATUS current
			DESCRIPTION
				"  "
			::= { hwInfoBBUEntry 8 }
		
		-- 1.3.6.1.4.1.34774.4.1.23.5.5.1.9
		hwInfoBBUDeliveredOn OBJECT-TYPE
			SYNTAX OCTET STRING
			MAX-ACCESS read-only
			STATUS current
			DESCRIPTION
				"  "
			::= { hwInfoBBUEntry 9 }
		
		-- 1.3.6.1.4.1.34774.4.1.23.5.5.1.10
		hwInfoBBUOwningController OBJECT-TYPE
			SYNTAX OCTET STRING
			MAX-ACCESS read-only
			STATUS current
			DESCRIPTION
				"  "
			::= { hwInfoBBUEntry 10 }
		
		-- 1.3.6.1.4.1.34774.4.1.23.5.5.1.11
		hwInfoBBUElectronicLabel OBJECT-TYPE
			SYNTAX OCTET STRING
			MAX-ACCESS read-only
			STATUS current
			DESCRIPTION
				"  "
			::= { hwInfoBBUEntry 11 }
		
		-- 1.3.6.1.4.1.34774.4.1.23.5.6
		hwInfoEnclosureTable OBJECT-TYPE
			SYNTAX SEQUENCE OF HwInfoEnclosureEntry
			MAX-ACCESS not-accessible
			STATUS current
			DESCRIPTION
				" "
			::= { hwHardwareInfo 6 }
		
		-- 1.3.6.1.4.1.34774.4.1.23.5.6.1
		hwInfoEnclosureEntry OBJECT-TYPE
			SYNTAX HwInfoEnclosureEntry
			MAX-ACCESS not-accessible
			STATUS current
			DESCRIPTION
				" "
			INDEX { hwInfoEnclosureID }
			::= { hwInfoEnclosureTable 1 }
		
		HwInfoEnclosureEntry ::=
			SEQUENCE { 
				hwInfoEnclosureID
					OCTET STRING,
				hwInfoEnclosureName
					OCTET STRING,
				hwInfoEnclosureLogicType
					Unsigned32,
				hwInfoEnclosureHealthStatus
					Unsigned32,
				hwInfoEnclosureRunningStatus
					Unsigned32,
				hwInfoEnclosureLocation
					OCTET STRING,
				hwInfoEnclosureType
					Unsigned32,
				hwInfoEnclosureTemperature
					Integer32,
				hwInfoEnclosureSN
					OCTET STRING,
				hwInfoEnclosureMAC
					OCTET STRING,
				hwInfoEnclosureHeight
					Unsigned32,
				hwInfoEnclosureExpansionDepth
					Unsigned32,
				hwInfoEnclosureElectronicLabel
					OCTET STRING
			 }

		-- 1.3.6.1.4.1.34774.4.1.23.5.6.1.1
		hwInfoEnclosureID OBJECT-TYPE
			SYNTAX OCTET STRING
			MAX-ACCESS read-only
			STATUS current
			DESCRIPTION
				" "
			::= { hwInfoEnclosureEntry 1 }
		
		-- 1.3.6.1.4.1.34774.4.1.23.5.6.1.2
		hwInfoEnclosureName OBJECT-TYPE
			SYNTAX OCTET STRING
			MAX-ACCESS read-only
			STATUS current
			DESCRIPTION
				" "
			::= { hwInfoEnclosureEntry 2 }
		
		-- 1.3.6.1.4.1.34774.4.1.23.5.6.1.3
		hwInfoEnclosureLogicType OBJECT-TYPE
			SYNTAX Unsigned32
			MAX-ACCESS read-only
			STATUS current
			DESCRIPTION
				" "
			::= { hwInfoEnclosureEntry 3 }
		
		-- 1.3.6.1.4.1.34774.4.1.23.5.6.1.4
		hwInfoEnclosureHealthStatus OBJECT-TYPE
			SYNTAX Unsigned32
			MAX-ACCESS read-only
			STATUS current
			DESCRIPTION
				" "
			::= { hwInfoEnclosureEntry 4 }
		
		-- 1.3.6.1.4.1.34774.4.1.23.5.6.1.5
		hwInfoEnclosureRunningStatus OBJECT-TYPE
			SYNTAX Unsigned32
			MAX-ACCESS read-only
			STATUS current
			DESCRIPTION
				" "
			::= { hwInfoEnclosureEntry 5 }
		
		-- 1.3.6.1.4.1.34774.4.1.23.5.6.1.6
		hwInfoEnclosureLocation OBJECT-TYPE
			SYNTAX OCTET STRING
			MAX-ACCESS read-only
			STATUS current
			DESCRIPTION
				" "
			::= { hwInfoEnclosureEntry 6 }
		
		-- 1.3.6.1.4.1.34774.4.1.23.5.6.1.7
		hwInfoEnclosureType OBJECT-TYPE
			SYNTAX Unsigned32
			MAX-ACCESS read-only
			STATUS current
			DESCRIPTION
				" "
			::= { hwInfoEnclosureEntry 7 }
		
		-- 1.3.6.1.4.1.34774.4.1.23.5.6.1.8
		hwInfoEnclosureTemperature OBJECT-TYPE
			SYNTAX Integer32
			MAX-ACCESS read-only
			STATUS current
			DESCRIPTION
				" "
			::= { hwInfoEnclosureEntry 8 }
		
		-- 1.3.6.1.4.1.34774.4.1.23.5.6.1.9
		hwInfoEnclosureSN OBJECT-TYPE
			SYNTAX OCTET STRING
			MAX-ACCESS read-only
			STATUS current
			DESCRIPTION
				" "
			::= { hwInfoEnclosureEntry 9 }
		
		-- 1.3.6.1.4.1.34774.4.1.23.5.6.1.10
		hwInfoEnclosureMAC OBJECT-TYPE
			SYNTAX OCTET STRING
			MAX-ACCESS read-only
			STATUS current
			DESCRIPTION
				" "
			::= { hwInfoEnclosureEntry 10 }
		
		-- 1.3.6.1.4.1.34774.4.1.23.5.6.1.11
		hwInfoEnclosureHeight OBJECT-TYPE
			SYNTAX Unsigned32
			MAX-ACCESS read-only
			STATUS current
			DESCRIPTION
				" "
			::= { hwInfoEnclosureEntry 11 }
		
		-- 1.3.6.1.4.1.34774.4.1.23.5.6.1.12
		hwInfoEnclosureExpansionDepth OBJECT-TYPE
			SYNTAX Unsigned32
			MAX-ACCESS read-only
			STATUS current
			DESCRIPTION
				" "
			::= { hwInfoEnclosureEntry 12 }
		
		-- 1.3.6.1.4.1.34774.4.1.23.5.6.1.13
		hwInfoEnclosureElectronicLabel OBJECT-TYPE
			SYNTAX OCTET STRING
			MAX-ACCESS read-only
			STATUS current
			DESCRIPTION
				" "
			::= { hwInfoEnclosureEntry 13 }
		
		-- 1.3.6.1.4.1.34774.4.1.23.5.7
		hwInfoPortComTable OBJECT-TYPE
			SYNTAX SEQUENCE OF HwInfoPortComEntry
			MAX-ACCESS not-accessible
			STATUS current
			DESCRIPTION
				" "
			::= { hwHardwareInfo 7 }
		
		-- 1.3.6.1.4.1.34774.4.1.23.5.7.1
		hwInfoPortComEntry OBJECT-TYPE
			SYNTAX HwInfoPortComEntry
			MAX-ACCESS not-accessible
			STATUS current
			DESCRIPTION
				" "
			INDEX { hwInfoPortComID }
			::= { hwInfoPortComTable 1 }
		
		HwInfoPortComEntry ::=
			SEQUENCE { 
				hwInfoPortComID
					OCTET STRING,
				hwInfoPortComLocation
					OCTET STRING,
				hwInfoPortComHealthStatus
					Unsigned32,
				hwInfoPortComRunningStatus
					Unsigned32,
				hwInfoPortComType
					Unsigned32
			 }

		-- 1.3.6.1.4.1.34774.4.1.23.5.7.1.1
		hwInfoPortComID OBJECT-TYPE
			SYNTAX OCTET STRING
			MAX-ACCESS read-only
			STATUS current
			DESCRIPTION
				" "
			::= { hwInfoPortComEntry 1 }
		
		-- 1.3.6.1.4.1.34774.4.1.23.5.7.1.2
		hwInfoPortComLocation OBJECT-TYPE
			SYNTAX OCTET STRING
			MAX-ACCESS read-only
			STATUS current
			DESCRIPTION
				" "
			::= { hwInfoPortComEntry 2 }
		
		-- 1.3.6.1.4.1.34774.4.1.23.5.7.1.3
		hwInfoPortComHealthStatus OBJECT-TYPE
			SYNTAX Unsigned32
			MAX-ACCESS read-only
			STATUS current
			DESCRIPTION
				" "
			::= { hwInfoPortComEntry 3 }
		
		-- 1.3.6.1.4.1.34774.4.1.23.5.7.1.4
		hwInfoPortComRunningStatus OBJECT-TYPE
			SYNTAX Unsigned32
			MAX-ACCESS read-only
			STATUS current
			DESCRIPTION
				" "
			::= { hwInfoPortComEntry 4 }
		
		-- 1.3.6.1.4.1.34774.4.1.23.5.7.1.5
		hwInfoPortComType OBJECT-TYPE
			SYNTAX Unsigned32
			MAX-ACCESS read-only
			STATUS current
			DESCRIPTION
				" "
			::= { hwInfoPortComEntry 5 }
		
		-- 1.3.6.1.4.1.34774.4.1.23.5.8
		hwInfoPortEthTable OBJECT-TYPE
			SYNTAX SEQUENCE OF HwInfoPortEthEntry
			MAX-ACCESS not-accessible
			STATUS current
			DESCRIPTION
				" "
			::= { hwHardwareInfo 8 }
		
		-- 1.3.6.1.4.1.34774.4.1.23.5.8.1
		hwInfoPortEthEntry OBJECT-TYPE
			SYNTAX HwInfoPortEthEntry
			MAX-ACCESS not-accessible
			STATUS current
			DESCRIPTION
				" "
			INDEX { hwInfoPortEthID }
			::= { hwInfoPortEthTable 1 }
		
		HwInfoPortEthEntry ::=
			SEQUENCE { 
				hwInfoPortEthID
					OCTET STRING,
				hwInfoPortEthLocation
					OCTET STRING,
				hwInfoPortEthHealthStatus
					Unsigned32,
				hwInfoPortEthRunningStatus
					Unsigned32,
				hwInfoPortEthType
					Unsigned32,
				hwInfoPortEthIPv4Address
					OCTET STRING,
				hwInfoPortEthSubnetMask
					OCTET STRING,
				hwInfoPortEthIPv4Gateway
					OCTET STRING,
				hwInfoPortEthIPv6Address
					OCTET STRING,
				hwInfoPortEthIPv6PrefixLength
					OCTET STRING,
				hwInfoPortEthIPv6Gateway
					OCTET STRING,
				hwInfoPortEthMAC
					OCTET STRING,
				hwInfoPortEthRole
					Unsigned32,
				hwInfoPortEthMode
					Unsigned32,
				hwInfoPortEthMTU
					Unsigned32,
				hwInfoPortEthWorkingRate
					Unsigned32,
				hwInfoPortEthBondName
					OCTET STRING,
				hwInfoPortEthiSCSIPort
					OCTET STRING,
				hwInfoPortEthiSCSIName
					OCTET STRING,
				hwInfoPortEthErrorPackets
					Unsigned32,
				hwInfoPortEthLostPackages
					Unsigned32,
				hwInfoPortEthStartTime
					OCTET STRING
			 }

		-- 1.3.6.1.4.1.34774.4.1.23.5.8.1.1
		hwInfoPortEthID OBJECT-TYPE
			SYNTAX OCTET STRING
			MAX-ACCESS read-only
			STATUS current
			DESCRIPTION
				" "
			::= { hwInfoPortEthEntry 1 }
		
		-- 1.3.6.1.4.1.34774.4.1.23.5.8.1.2
		hwInfoPortEthLocation OBJECT-TYPE
			SYNTAX OCTET STRING
			MAX-ACCESS read-only
			STATUS current
			DESCRIPTION
				" "
			::= { hwInfoPortEthEntry 2 }
		
		-- 1.3.6.1.4.1.34774.4.1.23.5.8.1.3
		hwInfoPortEthHealthStatus OBJECT-TYPE
			SYNTAX Unsigned32
			MAX-ACCESS read-only
			STATUS current
			DESCRIPTION
				" "
			::= { hwInfoPortEthEntry 3 }
		
		-- 1.3.6.1.4.1.34774.4.1.23.5.8.1.4
		hwInfoPortEthRunningStatus OBJECT-TYPE
			SYNTAX Unsigned32
			MAX-ACCESS read-only
			STATUS current
			DESCRIPTION
				" "
			::= { hwInfoPortEthEntry 4 }
		
		-- 1.3.6.1.4.1.34774.4.1.23.5.8.1.5
		hwInfoPortEthType OBJECT-TYPE
			SYNTAX Unsigned32
			MAX-ACCESS read-only
			STATUS current
			DESCRIPTION
				" "
			::= { hwInfoPortEthEntry 5 }
		
		-- 1.3.6.1.4.1.34774.4.1.23.5.8.1.6
		hwInfoPortEthIPv4Address OBJECT-TYPE
			SYNTAX OCTET STRING
			MAX-ACCESS read-only
			STATUS current
			DESCRIPTION
				"  "
			::= { hwInfoPortEthEntry 6 }
		
		-- 1.3.6.1.4.1.34774.4.1.23.5.8.1.7
		hwInfoPortEthSubnetMask OBJECT-TYPE
			SYNTAX OCTET STRING
			MAX-ACCESS read-only
			STATUS current
			DESCRIPTION
				"  "
			::= { hwInfoPortEthEntry 7 }
		
		-- 1.3.6.1.4.1.34774.4.1.23.5.8.1.8
		hwInfoPortEthIPv4Gateway OBJECT-TYPE
			SYNTAX OCTET STRING
			MAX-ACCESS read-only
			STATUS current
			DESCRIPTION
				"  "
			::= { hwInfoPortEthEntry 8 }
		
		-- 1.3.6.1.4.1.34774.4.1.23.5.8.1.9
		hwInfoPortEthIPv6Address OBJECT-TYPE
			SYNTAX OCTET STRING
			MAX-ACCESS read-only
			STATUS current
			DESCRIPTION
				" "
			::= { hwInfoPortEthEntry 9 }
		
		-- 1.3.6.1.4.1.34774.4.1.23.5.8.1.10
		hwInfoPortEthIPv6PrefixLength OBJECT-TYPE
			SYNTAX OCTET STRING
			MAX-ACCESS read-only
			STATUS current
			DESCRIPTION
				" "
			::= { hwInfoPortEthEntry 10 }
		
		-- 1.3.6.1.4.1.34774.4.1.23.5.8.1.11
		hwInfoPortEthIPv6Gateway OBJECT-TYPE
			SYNTAX OCTET STRING
			MAX-ACCESS read-only
			STATUS current
			DESCRIPTION
				" "
			::= { hwInfoPortEthEntry 11 }
		
		-- 1.3.6.1.4.1.34774.4.1.23.5.8.1.12
		hwInfoPortEthMAC OBJECT-TYPE
			SYNTAX OCTET STRING
			MAX-ACCESS read-only
			STATUS current
			DESCRIPTION
				" "
			::= { hwInfoPortEthEntry 12 }
		
		-- 1.3.6.1.4.1.34774.4.1.23.5.8.1.13
		hwInfoPortEthRole OBJECT-TYPE
			SYNTAX Unsigned32
			MAX-ACCESS read-only
			STATUS current
			DESCRIPTION
				" "
			::= { hwInfoPortEthEntry 13 }
		
		-- 1.3.6.1.4.1.34774.4.1.23.5.8.1.14
		hwInfoPortEthMode OBJECT-TYPE
			SYNTAX Unsigned32
			MAX-ACCESS read-only
			STATUS current
			DESCRIPTION
				"  "
			::= { hwInfoPortEthEntry 14 }
		
		-- 1.3.6.1.4.1.34774.4.1.23.5.8.1.15
		hwInfoPortEthMTU OBJECT-TYPE
			SYNTAX Unsigned32
			MAX-ACCESS read-only
			STATUS current
			DESCRIPTION
				" "
			::= { hwInfoPortEthEntry 15 }
		
		-- 1.3.6.1.4.1.34774.4.1.23.5.8.1.16
		hwInfoPortEthWorkingRate OBJECT-TYPE
			SYNTAX Unsigned32
			MAX-ACCESS read-only
			STATUS current
			DESCRIPTION
				" "
			::= { hwInfoPortEthEntry 16 }
		
		-- 1.3.6.1.4.1.34774.4.1.23.5.8.1.17
		hwInfoPortEthBondName OBJECT-TYPE
			SYNTAX OCTET STRING
			MAX-ACCESS read-only
			STATUS current
			DESCRIPTION
				" "
			::= { hwInfoPortEthEntry 17 }
		
		-- 1.3.6.1.4.1.34774.4.1.23.5.8.1.18
		hwInfoPortEthiSCSIPort OBJECT-TYPE
			SYNTAX OCTET STRING
			MAX-ACCESS read-only
			STATUS current
			DESCRIPTION
				"  "
			::= { hwInfoPortEthEntry 18 }
		
		-- 1.3.6.1.4.1.34774.4.1.23.5.8.1.19
		hwInfoPortEthiSCSIName OBJECT-TYPE
			SYNTAX OCTET STRING
			MAX-ACCESS read-only
			STATUS current
			DESCRIPTION
				"  "
			::= { hwInfoPortEthEntry 19 }
		
		-- 1.3.6.1.4.1.34774.4.1.23.5.8.1.20
		hwInfoPortEthErrorPackets OBJECT-TYPE
			SYNTAX Unsigned32
			MAX-ACCESS read-only
			STATUS current
			DESCRIPTION
				"  "
			::= { hwInfoPortEthEntry 20 }
		
		-- 1.3.6.1.4.1.34774.4.1.23.5.8.1.21
		hwInfoPortEthLostPackages OBJECT-TYPE
			SYNTAX Unsigned32
			MAX-ACCESS read-only
			STATUS current
			DESCRIPTION
				" "
			::= { hwInfoPortEthEntry 21 }
		
		-- 1.3.6.1.4.1.34774.4.1.23.5.8.1.22
		hwInfoPortEthStartTime OBJECT-TYPE
			SYNTAX OCTET STRING
			MAX-ACCESS read-only
			STATUS current
			DESCRIPTION
				" "
			::= { hwInfoPortEthEntry 22 }
		
		-- 1.3.6.1.4.1.34774.4.1.23.5.9
		hwInfoPortFCTable OBJECT-TYPE
			SYNTAX SEQUENCE OF HwInfoPortFCEntry
			MAX-ACCESS not-accessible
			STATUS current
			DESCRIPTION
				" "
			::= { hwHardwareInfo 9 }
		
		-- 1.3.6.1.4.1.34774.4.1.23.5.9.1
		hwInfoPortFCEntry OBJECT-TYPE
			SYNTAX HwInfoPortFCEntry
			MAX-ACCESS not-accessible
			STATUS current
			DESCRIPTION
				" "
			INDEX { hwInfoPortFCID }
			::= { hwInfoPortFCTable 1 }
		
		HwInfoPortFCEntry ::=
			SEQUENCE { 
				hwInfoPortFCID
					OCTET STRING,
				hwInfoPortFCLocation
					OCTET STRING,
				hwInfoPortFCHealthStatus
					Unsigned32,
				hwInfoPortFCRunningStatus
					Unsigned32,
				hwInfoPortFCType
					Unsigned32,
				hwInfoPortFCWorkingRate
					Unsigned32,
				hwInfoPortFCConfiguredSpeed
					Unsigned32,
				hwInfoPortFCWWN
					OCTET STRING,
				hwInfoPortFCRole
					Unsigned32,
				hwInfoPortFCSFPStatus
					Unsigned32,
				hwInfoPortFCWorkingMode
					Unsigned32,
				hwInfoPortFCConfiguredMode
					Unsigned32,
				hwInfoPortFCFloginDelayTimes
					Unsigned32,
				hwInfoPortFCLostSignals
					Unsigned32,
				hwInfoPortFCLinkErrorsCodes
					Unsigned32,
				hwInfoPortFCLostSynchronizations
					Unsigned32,
				hwInfoPortFCFailedConnections
					Unsigned32,
				hwInfoPortFCStartTime
					OCTET STRING
			 }

		-- 1.3.6.1.4.1.34774.4.1.23.5.9.1.1
		hwInfoPortFCID OBJECT-TYPE
			SYNTAX OCTET STRING
			MAX-ACCESS read-only
			STATUS current
			DESCRIPTION
				" "
			::= { hwInfoPortFCEntry 1 }
		
		-- 1.3.6.1.4.1.34774.4.1.23.5.9.1.2
		hwInfoPortFCLocation OBJECT-TYPE
			SYNTAX OCTET STRING
			MAX-ACCESS read-only
			STATUS current
			DESCRIPTION
				" "
			::= { hwInfoPortFCEntry 2 }
		
		-- 1.3.6.1.4.1.34774.4.1.23.5.9.1.3
		hwInfoPortFCHealthStatus OBJECT-TYPE
			SYNTAX Unsigned32
			MAX-ACCESS read-only
			STATUS current
			DESCRIPTION
				" "
			::= { hwInfoPortFCEntry 3 }
		
		-- 1.3.6.1.4.1.34774.4.1.23.5.9.1.4
		hwInfoPortFCRunningStatus OBJECT-TYPE
			SYNTAX Unsigned32
			MAX-ACCESS read-only
			STATUS current
			DESCRIPTION
				" "
			::= { hwInfoPortFCEntry 4 }
		
		-- 1.3.6.1.4.1.34774.4.1.23.5.9.1.5
		hwInfoPortFCType OBJECT-TYPE
			SYNTAX Unsigned32
			MAX-ACCESS read-only
			STATUS current
			DESCRIPTION
				" "
			::= { hwInfoPortFCEntry 5 }
		
		-- 1.3.6.1.4.1.34774.4.1.23.5.9.1.6
		hwInfoPortFCWorkingRate OBJECT-TYPE
			SYNTAX Unsigned32
			MAX-ACCESS read-only
			STATUS current
			DESCRIPTION
				" "
			::= { hwInfoPortFCEntry 6 }
		
		-- 1.3.6.1.4.1.34774.4.1.23.5.9.1.7
		hwInfoPortFCConfiguredSpeed OBJECT-TYPE
			SYNTAX Unsigned32
			MAX-ACCESS read-only
			STATUS current
			DESCRIPTION
				" "
			::= { hwInfoPortFCEntry 7 }
		
		-- 1.3.6.1.4.1.34774.4.1.23.5.9.1.8
		hwInfoPortFCWWN OBJECT-TYPE
			SYNTAX OCTET STRING
			MAX-ACCESS read-only
			STATUS current
			DESCRIPTION
				" "
			::= { hwInfoPortFCEntry 8 }
		
		-- 1.3.6.1.4.1.34774.4.1.23.5.9.1.9
		hwInfoPortFCRole OBJECT-TYPE
			SYNTAX Unsigned32
			MAX-ACCESS read-only
			STATUS current
			DESCRIPTION
				" "
			::= { hwInfoPortFCEntry 9 }
		
		-- 1.3.6.1.4.1.34774.4.1.23.5.9.1.10
		hwInfoPortFCSFPStatus OBJECT-TYPE
			SYNTAX Unsigned32
			MAX-ACCESS read-only
			STATUS current
			DESCRIPTION
				" "
			::= { hwInfoPortFCEntry 10 }
		
		-- 1.3.6.1.4.1.34774.4.1.23.5.9.1.11
		hwInfoPortFCWorkingMode OBJECT-TYPE
			SYNTAX Unsigned32
			MAX-ACCESS read-only
			STATUS current
			DESCRIPTION
				" "
			::= { hwInfoPortFCEntry 11 }
		
		-- 1.3.6.1.4.1.34774.4.1.23.5.9.1.12
		hwInfoPortFCConfiguredMode OBJECT-TYPE
			SYNTAX Unsigned32
			MAX-ACCESS read-only
			STATUS current
			DESCRIPTION
				" "
			::= { hwInfoPortFCEntry 12 }
		
		-- 1.3.6.1.4.1.34774.4.1.23.5.9.1.13
		hwInfoPortFCFloginDelayTimes OBJECT-TYPE
			SYNTAX Unsigned32
			MAX-ACCESS read-only
			STATUS current
			DESCRIPTION
				" "
			::= { hwInfoPortFCEntry 13 }
		
		-- 1.3.6.1.4.1.34774.4.1.23.5.9.1.14
		hwInfoPortFCLostSignals OBJECT-TYPE
			SYNTAX Unsigned32
			MAX-ACCESS read-only
			STATUS current
			DESCRIPTION
				" "
			::= { hwInfoPortFCEntry 14 }
		
		-- 1.3.6.1.4.1.34774.4.1.23.5.9.1.15
		hwInfoPortFCLinkErrorsCodes OBJECT-TYPE
			SYNTAX Unsigned32
			MAX-ACCESS read-only
			STATUS current
			DESCRIPTION
				" "
			::= { hwInfoPortFCEntry 15 }
		
		-- 1.3.6.1.4.1.34774.4.1.23.5.9.1.16
		hwInfoPortFCLostSynchronizations OBJECT-TYPE
			SYNTAX Unsigned32
			MAX-ACCESS read-only
			STATUS current
			DESCRIPTION
				" "
			::= { hwInfoPortFCEntry 16 }
		
		-- 1.3.6.1.4.1.34774.4.1.23.5.9.1.17
		hwInfoPortFCFailedConnections OBJECT-TYPE
			SYNTAX Unsigned32
			MAX-ACCESS read-only
			STATUS current
			DESCRIPTION
				" "
			::= { hwInfoPortFCEntry 17 }
		
		-- 1.3.6.1.4.1.34774.4.1.23.5.9.1.18
		hwInfoPortFCStartTime OBJECT-TYPE
			SYNTAX OCTET STRING
			MAX-ACCESS read-only
			STATUS current
			DESCRIPTION
				" "
			::= { hwInfoPortFCEntry 18 }
		
		-- 1.3.6.1.4.1.34774.4.1.23.5.11
		hwInfoPortPCIETable OBJECT-TYPE
			SYNTAX SEQUENCE OF HwInfoPortPCIEEntry
			MAX-ACCESS not-accessible
			STATUS current
			DESCRIPTION
				" "
			::= { hwHardwareInfo 11 }
		
		-- 1.3.6.1.4.1.34774.4.1.23.5.11.1
		hwInfoPortPCIEEntry OBJECT-TYPE
			SYNTAX HwInfoPortPCIEEntry
			MAX-ACCESS not-accessible
			STATUS current
			DESCRIPTION
				" "
			INDEX { hwInfoPortPCIEID }
			::= { hwInfoPortPCIETable 1 }
		
		HwInfoPortPCIEEntry ::=
			SEQUENCE { 
				hwInfoPortPCIEID
					OCTET STRING,
				hwInfoPortPCIELocation
					OCTET STRING,
				hwInfoPortPCIEHealthStatus
					Unsigned32,
				hwInfoPortPCIERunningStatus
					Unsigned32,
				hwInfoPortPCIESpeed
					Unsigned32,
				hwInfoPortPCIECurrentPeerPortID
					OCTET STRING,
				hwInfoPortPCIESuggestPeerPortID
					OCTET STRING,
				hwInfoPortPCIELostSignals
					Unsigned32,
				hwInfoPortPCIEECRCError
					Unsigned32,
				hwInfoPortPCIEBadTlp
					Unsigned32,
				hwInfoPortPCIEBadDllp
					Unsigned32,
				hwInfoPortPCIERecvError
					Unsigned32,
				hwInfoPortPCIEChipEccError
					Unsigned32,
				hwInfoPortPCIEStartTime
					OCTET STRING
			 }

		-- 1.3.6.1.4.1.34774.4.1.23.5.11.1.1
		hwInfoPortPCIEID OBJECT-TYPE
			SYNTAX OCTET STRING
			MAX-ACCESS read-only
			STATUS current
			DESCRIPTION
				" "
			::= { hwInfoPortPCIEEntry 1 }
		
		-- 1.3.6.1.4.1.34774.4.1.23.5.11.1.2
		hwInfoPortPCIELocation OBJECT-TYPE
			SYNTAX OCTET STRING
			MAX-ACCESS read-only
			STATUS current
			DESCRIPTION
				" "
			::= { hwInfoPortPCIEEntry 2 }
		
		-- 1.3.6.1.4.1.34774.4.1.23.5.11.1.3
		hwInfoPortPCIEHealthStatus OBJECT-TYPE
			SYNTAX Unsigned32
			MAX-ACCESS read-only
			STATUS current
			DESCRIPTION
				" "
			::= { hwInfoPortPCIEEntry 3 }
		
		-- 1.3.6.1.4.1.34774.4.1.23.5.11.1.4
		hwInfoPortPCIERunningStatus OBJECT-TYPE
			SYNTAX Unsigned32
			MAX-ACCESS read-only
			STATUS current
			DESCRIPTION
				" "
			::= { hwInfoPortPCIEEntry 4 }
		
		-- 1.3.6.1.4.1.34774.4.1.23.5.11.1.5
		hwInfoPortPCIESpeed OBJECT-TYPE
			SYNTAX Unsigned32
			MAX-ACCESS read-only
			STATUS current
			DESCRIPTION
				" "
			::= { hwInfoPortPCIEEntry 5 }
		
		-- 1.3.6.1.4.1.34774.4.1.23.5.11.1.6
		hwInfoPortPCIECurrentPeerPortID OBJECT-TYPE
			SYNTAX OCTET STRING
			MAX-ACCESS read-only
			STATUS current
			DESCRIPTION
				"  "
			::= { hwInfoPortPCIEEntry 6 }
		
		-- 1.3.6.1.4.1.34774.4.1.23.5.11.1.7
		hwInfoPortPCIESuggestPeerPortID OBJECT-TYPE
			SYNTAX OCTET STRING
			MAX-ACCESS read-only
			STATUS current
			DESCRIPTION
				"  "
			::= { hwInfoPortPCIEEntry 7 }
		
		-- 1.3.6.1.4.1.34774.4.1.23.5.11.1.8
		hwInfoPortPCIELostSignals OBJECT-TYPE
			SYNTAX Unsigned32
			MAX-ACCESS read-only
			STATUS current
			DESCRIPTION
				"  "
			::= { hwInfoPortPCIEEntry 8 }
		
		-- 1.3.6.1.4.1.34774.4.1.23.5.11.1.9
		hwInfoPortPCIEECRCError OBJECT-TYPE
			SYNTAX Unsigned32
			MAX-ACCESS read-only
			STATUS current
			DESCRIPTION
				" "
			::= { hwInfoPortPCIEEntry 9 }
		
		-- 1.3.6.1.4.1.34774.4.1.23.5.11.1.10
		hwInfoPortPCIEBadTlp OBJECT-TYPE
			SYNTAX Unsigned32
			MAX-ACCESS read-only
			STATUS current
			DESCRIPTION
				" "
			::= { hwInfoPortPCIEEntry 10 }
		
		-- 1.3.6.1.4.1.34774.4.1.23.5.11.1.11
		hwInfoPortPCIEBadDllp OBJECT-TYPE
			SYNTAX Unsigned32
			MAX-ACCESS read-only
			STATUS current
			DESCRIPTION
				" "
			::= { hwInfoPortPCIEEntry 11 }
		
		-- 1.3.6.1.4.1.34774.4.1.23.5.11.1.12
		hwInfoPortPCIERecvError OBJECT-TYPE
			SYNTAX Unsigned32
			MAX-ACCESS read-only
			STATUS current
			DESCRIPTION
				" "
			::= { hwInfoPortPCIEEntry 12 }
		
		-- 1.3.6.1.4.1.34774.4.1.23.5.11.1.13
		hwInfoPortPCIEChipEccError OBJECT-TYPE
			SYNTAX Unsigned32
			MAX-ACCESS read-only
			STATUS current
			DESCRIPTION
				" "
			::= { hwInfoPortPCIEEntry 13 }
		
		-- 1.3.6.1.4.1.34774.4.1.23.5.11.1.14
		hwInfoPortPCIEStartTime OBJECT-TYPE
			SYNTAX OCTET STRING
			MAX-ACCESS read-only
			STATUS current
			DESCRIPTION
				"  "
			::= { hwInfoPortPCIEEntry 14 }
		
		-- 1.3.6.1.4.1.34774.4.1.23.5.12
		hwInfoPortSASTable OBJECT-TYPE
			SYNTAX SEQUENCE OF HwInfoPortSASEntry
			MAX-ACCESS not-accessible
			STATUS current
			DESCRIPTION
				" "
			::= { hwHardwareInfo 12 }
		
		-- 1.3.6.1.4.1.34774.4.1.23.5.12.1
		hwInfoPortSASEntry OBJECT-TYPE
			SYNTAX HwInfoPortSASEntry
			MAX-ACCESS not-accessible
			STATUS current
			DESCRIPTION
				"  "
			INDEX { hwInfoPortSASID }
			::= { hwInfoPortSASTable 1 }
		
		HwInfoPortSASEntry ::=
			SEQUENCE { 
				hwInfoPortSASID
					OCTET STRING,
				hwInfoPortSASLocation
					OCTET STRING,
				hwInfoPortSASHealthStatus
					Unsigned32,
				hwInfoPortSASRunningStatus
					Unsigned32,
				hwInfoPortSASType
					Unsigned32,
				hwInfoPortSASWorkingRate
					Unsigned32,
				hwInfoPortSASWWN
					OCTET STRING,
				hwInfoPortSASRole
					Unsigned32,
				hwInfoPortSASInvalidDword
					Unsigned32,
				hwInfoPortSASConsistErrors
					Unsigned32,
				hwInfoPortSASLossOfDword
					Unsigned32,
				hwInfoPortSASPHYResetErrors
					Unsigned32,
				hwInfoPortSASStartTime
					OCTET STRING,
				hwInfoPortSASEnabled
					Unsigned32
			 }

		-- 1.3.6.1.4.1.34774.4.1.23.5.12.1.1
		hwInfoPortSASID OBJECT-TYPE
			SYNTAX OCTET STRING
			MAX-ACCESS read-only
			STATUS current
			DESCRIPTION
				"  "
			::= { hwInfoPortSASEntry 1 }
		
		-- 1.3.6.1.4.1.34774.4.1.23.5.12.1.2
		hwInfoPortSASLocation OBJECT-TYPE
			SYNTAX OCTET STRING
			MAX-ACCESS read-only
			STATUS current
			DESCRIPTION
				"  "
			::= { hwInfoPortSASEntry 2 }
		
		-- 1.3.6.1.4.1.34774.4.1.23.5.12.1.3
		hwInfoPortSASHealthStatus OBJECT-TYPE
			SYNTAX Unsigned32
			MAX-ACCESS read-only
			STATUS current
			DESCRIPTION
				" "
			::= { hwInfoPortSASEntry 3 }
		
		-- 1.3.6.1.4.1.34774.4.1.23.5.12.1.4
		hwInfoPortSASRunningStatus OBJECT-TYPE
			SYNTAX Unsigned32
			MAX-ACCESS read-only
			STATUS current
			DESCRIPTION
				"  "
			::= { hwInfoPortSASEntry 4 }
		
		-- 1.3.6.1.4.1.34774.4.1.23.5.12.1.5
		hwInfoPortSASType OBJECT-TYPE
			SYNTAX Unsigned32
			MAX-ACCESS read-only
			STATUS current
			DESCRIPTION
				" "
			::= { hwInfoPortSASEntry 5 }
		
		-- 1.3.6.1.4.1.34774.4.1.23.5.12.1.6
		hwInfoPortSASWorkingRate OBJECT-TYPE
			SYNTAX Unsigned32
			MAX-ACCESS read-only
			STATUS current
			DESCRIPTION
				"  "
			::= { hwInfoPortSASEntry 6 }
		
		-- 1.3.6.1.4.1.34774.4.1.23.5.12.1.7
		hwInfoPortSASWWN OBJECT-TYPE
			SYNTAX OCTET STRING
			MAX-ACCESS read-only
			STATUS current
			DESCRIPTION
				"  "
			::= { hwInfoPortSASEntry 7 }
		
		-- 1.3.6.1.4.1.34774.4.1.23.5.12.1.8
		hwInfoPortSASRole OBJECT-TYPE
			SYNTAX Unsigned32
			MAX-ACCESS read-only
			STATUS current
			DESCRIPTION
				"  "
			::= { hwInfoPortSASEntry 8 }
		
		-- 1.3.6.1.4.1.34774.4.1.23.5.12.1.9
		hwInfoPortSASInvalidDword OBJECT-TYPE
			SYNTAX Unsigned32
			MAX-ACCESS read-only
			STATUS current
			DESCRIPTION
				" "
			::= { hwInfoPortSASEntry 9 }
		
		-- 1.3.6.1.4.1.34774.4.1.23.5.12.1.10
		hwInfoPortSASConsistErrors OBJECT-TYPE
			SYNTAX Unsigned32
			MAX-ACCESS read-only
			STATUS current
			DESCRIPTION
				" "
			::= { hwInfoPortSASEntry 10 }
		
		-- 1.3.6.1.4.1.34774.4.1.23.5.12.1.11
		hwInfoPortSASLossOfDword OBJECT-TYPE
			SYNTAX Unsigned32
			MAX-ACCESS read-only
			STATUS current
			DESCRIPTION
				"  "
			::= { hwInfoPortSASEntry 11 }
		
		-- 1.3.6.1.4.1.34774.4.1.23.5.12.1.12
		hwInfoPortSASPHYResetErrors OBJECT-TYPE
			SYNTAX Unsigned32
			MAX-ACCESS read-only
			STATUS current
			DESCRIPTION
				"  "
			::= { hwInfoPortSASEntry 12 }
		
		-- 1.3.6.1.4.1.34774.4.1.23.5.12.1.13
		hwInfoPortSASStartTime OBJECT-TYPE
			SYNTAX OCTET STRING
			MAX-ACCESS read-only
			STATUS current
			DESCRIPTION
				"  "
			::= { hwInfoPortSASEntry 13 }
		
		-- 1.3.6.1.4.1.34774.4.1.23.5.12.1.14
		hwInfoPortSASEnabled OBJECT-TYPE
			SYNTAX Unsigned32
			MAX-ACCESS read-only
			STATUS current
			DESCRIPTION
				"  "
			::= { hwInfoPortSASEntry 14 }
		
		-- 1.3.6.1.4.1.34774.4.1.23.5.13
		hwInfoInterfaceModuleTable OBJECT-TYPE
			SYNTAX SEQUENCE OF HwInfoInterfaceModuleEntry
			MAX-ACCESS not-accessible
			STATUS current
			DESCRIPTION
				" "
			::= { hwHardwareInfo 13 }
		
		-- 1.3.6.1.4.1.34774.4.1.23.5.13.1
		hwInfoInterfaceModuleEntry OBJECT-TYPE
			SYNTAX HwInfoInterfaceModuleEntry
			MAX-ACCESS not-accessible
			STATUS current
			DESCRIPTION
				" "
			INDEX { hwInfoInterfaceModuleID }
			::= { hwInfoInterfaceModuleTable 1 }
		
		HwInfoInterfaceModuleEntry ::=
			SEQUENCE { 
				hwInfoInterfaceModuleID
					OCTET STRING,
				hwInfoInterfaceModuleLocation
					OCTET STRING,
				hwInfoInterfaceModuleHealthStatus
					Unsigned32,
				hwInfoInterfaceModuleRunningStatus
					Unsigned32,
				hwInfoInterfaceModuleModel
					Unsigned32,
				hwInfoInterfaceModuleLogicVersion
					OCTET STRING,
				hwInfoInterfaceModulePCBVersion
					OCTET STRING,
				hwInfoInterfaceModuleElectronicLabel
					OCTET STRING
			 }

		-- 1.3.6.1.4.1.34774.4.1.23.5.13.1.1
		hwInfoInterfaceModuleID OBJECT-TYPE
			SYNTAX OCTET STRING
			MAX-ACCESS read-only
			STATUS current
			DESCRIPTION
				" "
			::= { hwInfoInterfaceModuleEntry 1 }
		
		-- 1.3.6.1.4.1.34774.4.1.23.5.13.1.2
		hwInfoInterfaceModuleLocation OBJECT-TYPE
			SYNTAX OCTET STRING
			MAX-ACCESS read-only
			STATUS current
			DESCRIPTION
				" "
			::= { hwInfoInterfaceModuleEntry 2 }
		
		-- 1.3.6.1.4.1.34774.4.1.23.5.13.1.3
		hwInfoInterfaceModuleHealthStatus OBJECT-TYPE
			SYNTAX Unsigned32
			MAX-ACCESS read-only
			STATUS current
			DESCRIPTION
				"  "
			::= { hwInfoInterfaceModuleEntry 3 }
		
		-- 1.3.6.1.4.1.34774.4.1.23.5.13.1.4
		hwInfoInterfaceModuleRunningStatus OBJECT-TYPE
			SYNTAX Unsigned32
			MAX-ACCESS read-only
			STATUS current
			DESCRIPTION
				" "
			::= { hwInfoInterfaceModuleEntry 4 }
		
		-- 1.3.6.1.4.1.34774.4.1.23.5.13.1.5
		hwInfoInterfaceModuleModel OBJECT-TYPE
			SYNTAX Unsigned32
			MAX-ACCESS read-only
			STATUS current
			DESCRIPTION
				"  "
			::= { hwInfoInterfaceModuleEntry 5 }
		
		-- 1.3.6.1.4.1.34774.4.1.23.5.13.1.6
		hwInfoInterfaceModuleLogicVersion OBJECT-TYPE
			SYNTAX OCTET STRING
			MAX-ACCESS read-only
			STATUS current
			DESCRIPTION
				" "
			::= { hwInfoInterfaceModuleEntry 6 }
		
		-- 1.3.6.1.4.1.34774.4.1.23.5.13.1.7
		hwInfoInterfaceModulePCBVersion OBJECT-TYPE
			SYNTAX OCTET STRING
			MAX-ACCESS read-only
			STATUS current
			DESCRIPTION
				" "
			::= { hwInfoInterfaceModuleEntry 7 }
		
		-- 1.3.6.1.4.1.34774.4.1.23.5.13.1.8
		hwInfoInterfaceModuleElectronicLabel OBJECT-TYPE
			SYNTAX OCTET STRING
			MAX-ACCESS read-only
			STATUS current
			DESCRIPTION
				" "
			::= { hwInfoInterfaceModuleEntry 8 }
		
		-- 1.3.6.1.4.1.34774.4.1.23.5.14
		hwInfoExpBoardTable OBJECT-TYPE
			SYNTAX SEQUENCE OF HwInfoExpBoardEntry
			MAX-ACCESS not-accessible
			STATUS current
			DESCRIPTION
				" "
			::= { hwHardwareInfo 14 }
		
		-- 1.3.6.1.4.1.34774.4.1.23.5.14.1
		hwInfoExpBoardEntry OBJECT-TYPE
			SYNTAX HwInfoExpBoardEntry
			MAX-ACCESS not-accessible
			STATUS current
			DESCRIPTION
				" "
			INDEX { hwInfoExpBoardID }
			::= { hwInfoExpBoardTable 1 }
		
		HwInfoExpBoardEntry ::=
			SEQUENCE { 
				hwInfoExpBoardID
					OCTET STRING,
				hwInfoExpBoardLocation
					OCTET STRING,
				hwInfoExpBoardHealthStatus
					Unsigned32,
				hwInfoExpBoardRunningStatus
					Unsigned32,
				hwInfoExpBoardModel
					Unsigned32,
				hwInfoExpBoardLogicVersion
					OCTET STRING,
				hwInfoExpBoardPCBVersion
					OCTET STRING,
				hwInfoExpBoardSESVersion
					OCTET STRING,
				hwInfoExpBoardELabel
					OCTET STRING
			 }

		-- 1.3.6.1.4.1.34774.4.1.23.5.14.1.1
		hwInfoExpBoardID OBJECT-TYPE
			SYNTAX OCTET STRING
			MAX-ACCESS read-only
			STATUS current
			DESCRIPTION
				"  "
			::= { hwInfoExpBoardEntry 1 }
		
		-- 1.3.6.1.4.1.34774.4.1.23.5.14.1.2
		hwInfoExpBoardLocation OBJECT-TYPE
			SYNTAX OCTET STRING
			MAX-ACCESS read-only
			STATUS current
			DESCRIPTION
				"  "
			::= { hwInfoExpBoardEntry 2 }
		
		-- 1.3.6.1.4.1.34774.4.1.23.5.14.1.3
		hwInfoExpBoardHealthStatus OBJECT-TYPE
			SYNTAX Unsigned32
			MAX-ACCESS read-only
			STATUS current
			DESCRIPTION
				"  "
			::= { hwInfoExpBoardEntry 3 }
		
		-- 1.3.6.1.4.1.34774.4.1.23.5.14.1.4
		hwInfoExpBoardRunningStatus OBJECT-TYPE
			SYNTAX Unsigned32
			MAX-ACCESS read-only
			STATUS current
			DESCRIPTION
				"  "
			::= { hwInfoExpBoardEntry 4 }
		
		-- 1.3.6.1.4.1.34774.4.1.23.5.14.1.5
		hwInfoExpBoardModel OBJECT-TYPE
			SYNTAX Unsigned32
			MAX-ACCESS read-only
			STATUS current
			DESCRIPTION
				"  "
			::= { hwInfoExpBoardEntry 5 }
		
		-- 1.3.6.1.4.1.34774.4.1.23.5.14.1.6
		hwInfoExpBoardLogicVersion OBJECT-TYPE
			SYNTAX OCTET STRING
			MAX-ACCESS read-only
			STATUS current
			DESCRIPTION
				"  "
			::= { hwInfoExpBoardEntry 6 }
		
		-- 1.3.6.1.4.1.34774.4.1.23.5.14.1.7
		hwInfoExpBoardPCBVersion OBJECT-TYPE
			SYNTAX OCTET STRING
			MAX-ACCESS read-only
			STATUS current
			DESCRIPTION
				"  "
			::= { hwInfoExpBoardEntry 7 }
		
		-- 1.3.6.1.4.1.34774.4.1.23.5.14.1.8
		hwInfoExpBoardSESVersion OBJECT-TYPE
			SYNTAX OCTET STRING
			MAX-ACCESS read-only
			STATUS current
			DESCRIPTION
				"  "
			::= { hwInfoExpBoardEntry 8 }
		
		-- 1.3.6.1.4.1.34774.4.1.23.5.14.1.9
		hwInfoExpBoardELabel OBJECT-TYPE
			SYNTAX OCTET STRING
			MAX-ACCESS read-only
			STATUS current
			DESCRIPTION
				"  "
			::= { hwInfoExpBoardEntry 9 }
		
		-- 1.6
		isoConformance OBJECT IDENTIFIER ::= { iso 6 }
		
		-- 1.6.1
		isoGroups OBJECT IDENTIFIER ::= { isoConformance 1 }
		
		-- 1.6.1.1
		currentObjectGroup OBJECT-GROUP
			OBJECTS { hwInfoPortComID, hwInfoPortComLocation, hwInfoPortComHealthStatus, hwInfoPortComRunningStatus, hwInfoPortComType, 
				hwInfoPortEthID, hwInfoPortEthLocation, hwInfoPortEthHealthStatus, hwInfoPortEthRunningStatus, hwInfoPortEthType, 
				hwInfoPortEthIPv4Address, hwInfoPortEthSubnetMask, hwInfoPortEthIPv4Gateway, hwInfoPortEthIPv6Address, hwInfoPortEthIPv6PrefixLength, 
				hwInfoPortEthIPv6Gateway, hwInfoPortEthMAC, hwInfoPortEthRole, hwInfoPortEthMode, hwInfoPortEthMTU, 
				hwInfoPortEthWorkingRate, hwInfoPortEthBondName, hwInfoPortEthiSCSIPort, hwInfoPortEthiSCSIName, hwInfoPortEthErrorPackets, 
				hwInfoPortEthLostPackages, hwInfoPortFCID, hwInfoPortFCLocation, hwInfoPortFCHealthStatus, hwInfoPortFCRunningStatus, 
				hwInfoPortFCType, hwInfoPortFCWorkingRate, hwInfoPortFCConfiguredSpeed, hwInfoPortFCWWN, hwInfoPortFCRole, 
				hwInfoPortFCSFPStatus, hwInfoPortFCWorkingMode, hwInfoPortFCConfiguredMode, hwInfoPortFCFloginDelayTimes, hwInfoPortFCLostSignals, 
				hwInfoPortFCLinkErrorsCodes, hwInfoPortFCLostSynchronizations, hwInfoPortFCFailedConnections, hwInfoPortPCIEID, hwInfoPortPCIELocation, 
				hwInfoPortPCIEHealthStatus, hwInfoPortPCIERunningStatus, hwInfoPortPCIESpeed, hwInfoPortPCIECurrentPeerPortID, hwInfoPortPCIESuggestPeerPortID, 
				hwInfoPortPCIELostSignals, hwInfoPortPCIEECRCError, hwInfoPortPCIEBadTlp, hwInfoPortPCIERecvError, hwInfoPortPCIEChipEccError, 
				hwInfoPortSASID, hwInfoPortSASLocation, hwInfoPortSASHealthStatus, hwInfoPortSASRunningStatus, hwInfoPortSASType, 
				hwInfoPortSASWorkingRate, hwInfoPortSASWWN, hwInfoPortSASRole, hwInfoPortSASInvalidDword, hwInfoPortSASConsistErrors, 
				hwInfoPortSASLossOfDword, hwInfoPortSASPHYResetErrors, hwInfoPortSASStartTime, hwInfoPortSASEnabled, hwInfoInterfaceModuleID, 
				hwInfoInterfaceModuleLocation, hwInfoInterfaceModuleHealthStatus, hwInfoInterfaceModuleRunningStatus, hwInfoInterfaceModuleModel, hwInfoInterfaceModuleLogicVersion, 
				hwInfoInterfaceModulePCBVersion, hwInfoInterfaceModuleElectronicLabel, hwInfoDiskID, hwInfoDiskHealthStatus, hwInfoDiskRunningStatus, 
				hwInfoDiskType, hwInfoDiskCapacity, hwInfoDiskRole, hwInfoDiskSpeed, hwInfoDiskInterfaceBandwidth, 
				hwInfoDiskSectorSize, hwInfoDiskTemperature, hwInfoDiskModel, hwInfoDiskFirmwareVersion, hwInfoDiskManufacturer, 
				hwInfoDiskSerialNumber, hwInfoDiskLightStatus, hwInfoDiskDiskDomainID, hwInfoDiskDiskDomainName, hwInfoDiskDiskDomainTierID, 
				hwInfoDiskCofferDisk, hwInfoDiskRunTime, hwInfoDiskProgress, hwInfoDiskBarCode, hwInfoDiskCapacityUsage, 
				hwInfoDiskHealthMark, hwInfoDiskElectronicLabel, hwInfoControllerHealthStatus, hwInfoControllerRunningStatus, hwInfoControllerCPU, hwInfoControllerRole, 
				hwInfoControllerCacheCapacity, hwInfoControllerCPUUsage, hwInfoControllerMemoryUsage, hwInfoControllerVoltage, hwInfoControllerSoftwareVersion, 
				hwInfoControllerPCBVersion, hwInfoControllerSESVersion, hwInfoControllerBMCVersion, hwInfoControllerLogicVersion, hwInfoControllerBIOSVersion, 
				hwInfoControllerElectronicLabel, hwInfoPowerHealthStatus, hwInfoPowerRunningStatus, hwInfoPowerManufacturer, hwInfoPowerProduceDate, 
				hwInfoPowerSerialNumber, hwInfoFanHealthStatus, hwInfoFanElectronicLabel, hwInfoBBUHealthStatus, hwInfoBBURunningStatus, 
				hwInfoBBUType, hwInfoBBUNumberOfDischarges, hwInfoBBUFirmwareVersion, hwInfoBBUDeliveredOn, hwInfoBBUOwningController, 
				hwInfoBBUElectronicLabel, hwInfoEnclosureID, hwInfoEnclosureLogicType, hwInfoEnclosureHealthStatus, hwInfoEnclosureRunningStatus, 
				hwInfoEnclosureLocation, hwInfoEnclosureType, hwInfoEnclosureTemperature, hwInfoEnclosureSN, hwInfoEnclosureMAC, 
				hwInfoEnclosureHeight, hwInfoEnclosureExpansionDepth, hwInfoFanRunningStatus, hwInfoFanRunningLevel, hwInfoPowerModle, 
				hwInfoPowerVersion, hwInfoControllerID, hwInfoPowerID, hwInfoPowerType, hwInfoBBUID, 
				hwInfoControllerLocation, hwInfoDiskLocation, hwInfoEnclosureName, hwInfoEnclosureElectronicLabel, hwInfoPowerLocation, 
				hwInfoFanLocation, hwInfoBBULocation, hwInfoPortFCStartTime, hwInfoPortEthStartTime, hwInfoPortPCIEStartTime, 
				hwInfoExpBoardID, hwInfoExpBoardLocation, hwInfoExpBoardHealthStatus, hwInfoExpBoardRunningStatus, hwInfoExpBoardModel, 
				hwInfoExpBoardLogicVersion, hwInfoExpBoardPCBVersion, hwInfoExpBoardSESVersion, hwInfoExpBoardELabel, hwInfoBBUCurrentVoltage, 
				hwInfoFanID, hwInfoPortPCIEBadDllp }
			STATUS current
			DESCRIPTION 
				"Enter the description of the created OBJECT-GROUP."
			::= { isoGroups 1 }
		
		-- 1.6.2
		isoCompliances OBJECT IDENTIFIER ::= { isoConformance 2 }
		
--   this module
-- this module
		-- 1.6.2.1
		basicCompliance MODULE-COMPLIANCE
			STATUS current
			DESCRIPTION 
				"Enter the description of the created MODULE-COMPLIANCE."
			MODULE -- this module
				MANDATORY-GROUPS { currentObjectGroup }
			::= { isoCompliances 1 }
		
	
	END

--
-- HUAWEI-STORAGE-HARDWARE-MIB.mib
--
