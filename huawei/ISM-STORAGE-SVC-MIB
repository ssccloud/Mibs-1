--
-- ISM-STORAGE-SVC-MIB.mib
-- MIB generated by MG-SOFT Visual MIB Builder Version 4.0 Build 347
-- Thursday, March 27, 2014 at 11:54:11
--

	ISM-STORAGE-SVC-MIB DEFINITIONS ::= BEGIN
 
		IMPORTS
			OBJECT-GROUP, MODULE-COMPLIANCE			
				FROM SNMPv2-CONF			
			enterprises, IpAddress, Integer32, Unsigned32, 
			Gauge32, Counter64, OBJECT-TYPE, MODULE-IDENTITY			
				FROM SNMPv2-SMI			
			DisplayString, RowStatus, TEXTUAL-CONVENTION			
				FROM SNMPv2-TC;
	
	
		huaweistorage MODULE-IDENTITY 
			LAST-UPDATED "200809171628Z"		-- September 17, 2008 at 16:28 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"Description."
			REVISION "201304071915Z"		-- April 07, 2013 at 19:15 GMT
			DESCRIPTION 
				" "
			::= { enterprises 34774 }

		
	
--
-- Textual conventions
--
	
		NodeCodeString ::= TEXTUAL-CONVENTION
			DISPLAY-HINT 
				"255a"
			STATUS current
			DESCRIPTION 
				"characters in length."
			SYNTAX OCTET STRING (SIZE (15..17))

	
--
-- Node definitions
--
	
		hwStorage OBJECT IDENTIFIER ::= { huaweistorage 4 }

		
		hwISM OBJECT IDENTIFIER ::= { hwStorage 1 }

		
		common OBJECT IDENTIFIER ::= { hwISM 1 }

		
		deviceId OBJECT-TYPE
			SYNTAX DisplayString
			MAX-ACCESS read-only
			STATUS current
			DESCRIPTION
				"Description."
			::= { common 1 }

		
		deviceType OBJECT-TYPE
			SYNTAX Integer32
			MAX-ACCESS read-only
			STATUS current
			DESCRIPTION
				"Description."
			::= { common 2 }

		
		status OBJECT-TYPE
			SYNTAX Integer32
			MAX-ACCESS read-only
			STATUS current
			DESCRIPTION
				"Description."
			::= { common 3 }

		
		usedCapacity OBJECT-TYPE
			SYNTAX Counter64
			MAX-ACCESS read-only
			STATUS current
			DESCRIPTION
				"Description."
			::= { common 4 }

		
		totalCapacity OBJECT-TYPE
			SYNTAX Counter64
			MAX-ACCESS read-only
			STATUS current
			DESCRIPTION
				"Description."
			::= { common 5 }

		
		version OBJECT-TYPE
			SYNTAX DisplayString
			MAX-ACCESS read-only
			STATUS current
			DESCRIPTION
				"Description."
			::= { common 6 }

		
		deviceStatus OBJECT-TYPE
			SYNTAX Integer32
			MAX-ACCESS read-only
			STATUS current
			DESCRIPTION
				"Description."
			::= { common 7 }

		
		deviceTypeName OBJECT-TYPE
			SYNTAX OCTET STRING
			MAX-ACCESS read-only
			STATUS current
			DESCRIPTION
				"Description."
			::= { common 8 }

		
		totalDiskNumber OBJECT-TYPE
			SYNTAX Unsigned32
			MAX-ACCESS read-only
			STATUS current
			DESCRIPTION
				"The total number of Disks Array"
			::= { common 9 }

		
		managerPort OBJECT IDENTIFIER ::= { hwISM 5 }

		
		portNumber OBJECT-TYPE
			SYNTAX Integer32
			MAX-ACCESS read-write
			STATUS current
			DESCRIPTION
				"Description."
			::= { managerPort 1 }

		
		addrTable OBJECT-TYPE
			SYNTAX SEQUENCE OF AddrEntry
			MAX-ACCESS not-accessible
			STATUS current
			DESCRIPTION
				"Description."
			::= { managerPort 2 }

		
		addrEntry OBJECT-TYPE
			SYNTAX AddrEntry
			MAX-ACCESS not-accessible
			STATUS current
			DESCRIPTION
				"Description."
			INDEX { addrName }
			::= { addrTable 1 }

		
		AddrEntry ::=
			SEQUENCE { 
				addrName
					OCTET STRING,
				addrIP
					IpAddress
			 }

		addrName OBJECT-TYPE
			SYNTAX OCTET STRING (SIZE (0..64))
			MAX-ACCESS read-create
			STATUS current
			DESCRIPTION
				"Description."
			::= { addrEntry 1 }

		
		addrIP OBJECT-TYPE
			SYNTAX IpAddress
			MAX-ACCESS read-create
			STATUS current
			DESCRIPTION
				"Description."
			::= { addrEntry 2 }

		
		hwStorageService OBJECT IDENTIFIER ::= { hwISM 19 }

		
		hwVirtualArray OBJECT IDENTIFIER ::= { hwStorageService 1 }

		
		vis OBJECT IDENTIFIER ::= { hwVirtualArray 1 }

		
		hwNASGateway OBJECT IDENTIFIER ::= { hwStorageService 2 }

		
		hwArray OBJECT IDENTIFIER ::= { hwStorageService 3 }

		
		s2600 OBJECT IDENTIFIER ::= { hwArray 1 }

		
		s5000 OBJECT IDENTIFIER ::= { hwArray 2 }

		
		link OBJECT IDENTIFIER ::= { hwStorageService 4 }

		
		linkMode OBJECT-TYPE
			SYNTAX Gauge32
			MAX-ACCESS read-only
			STATUS current
			DESCRIPTION
				" "
			::= { link 2 }

		
		linkTable OBJECT-TYPE
			SYNTAX SEQUENCE OF LinkEntry
			MAX-ACCESS not-accessible
			STATUS current
			DESCRIPTION
				"Description."
			::= { link 3 }

		
		linkEntry OBJECT-TYPE
			SYNTAX LinkEntry
			MAX-ACCESS not-accessible
			STATUS current
			DESCRIPTION
				"Description."
			INDEX { linkWWN, linkIP }
			::= { linkTable 1 }

		
		LinkEntry ::=
			SEQUENCE { 
				linkWWN
					OCTET STRING,
				linkIP
					IpAddress,
				linkManagedRelation
					Gauge32
			 }

		linkWWN OBJECT-TYPE
			SYNTAX OCTET STRING (SIZE (0..64))
			MAX-ACCESS read-only
			STATUS current
			DESCRIPTION
				" "
			::= { linkEntry 1 }

		
		linkIP OBJECT-TYPE
			SYNTAX IpAddress
			MAX-ACCESS read-only
			STATUS current
			DESCRIPTION
				" "
			::= { linkEntry 2 }

		
		linkManagedRelation OBJECT-TYPE
			SYNTAX Gauge32
			MAX-ACCESS read-only
			STATUS current
			DESCRIPTION
				" "
			::= { linkEntry 3 }

		
		deployMap OBJECT IDENTIFIER ::= { hwStorageService 5 }

		
		deployMapTable OBJECT-TYPE
			SYNTAX SEQUENCE OF DeployMapEntry
			MAX-ACCESS not-accessible
			STATUS current
			DESCRIPTION
				"Description."
			::= { deployMap 1 }

		
		deployMapEntry OBJECT-TYPE
			SYNTAX DeployMapEntry
			MAX-ACCESS not-accessible
			STATUS current
			DESCRIPTION
				"Description."
			INDEX { deviceWwn }
			::= { deployMapTable 1 }

		
		DeployMapEntry ::=
			SEQUENCE { 
				deviceWwn
					OCTET STRING,
				deviceRoom
					Gauge32,
				deviceShelf
					Gauge32,
				deviceSlot
					Gauge32
			 }

		deviceWwn OBJECT-TYPE
			SYNTAX OCTET STRING (SIZE (0..64))
			MAX-ACCESS read-only
			STATUS current
			DESCRIPTION
				" "
			::= { deployMapEntry 1 }

		
		deviceRoom OBJECT-TYPE
			SYNTAX Gauge32
			MAX-ACCESS read-only
			STATUS current
			DESCRIPTION
				" "
			::= { deployMapEntry 2 }

		
		deviceShelf OBJECT-TYPE
			SYNTAX Gauge32
			MAX-ACCESS read-only
			STATUS current
			DESCRIPTION
				" "
			::= { deployMapEntry 3 }

		
		deviceSlot OBJECT-TYPE
			SYNTAX Gauge32
			MAX-ACCESS read-only
			STATUS current
			DESCRIPTION
				" "
			::= { deployMapEntry 4 }

		
		hwStoragePhysicalModule OBJECT IDENTIFIER ::= { hwStorageService 8 }

		
		hwStorageEnclosureTable OBJECT-TYPE
			SYNTAX SEQUENCE OF HwStorageEnclosureEntry
			MAX-ACCESS not-accessible
			STATUS current
			DESCRIPTION
				"Description."
			::= { hwStoragePhysicalModule 2 }

		
		hwStorageEnclosureEntry OBJECT-TYPE
			SYNTAX HwStorageEnclosureEntry
			MAX-ACCESS not-accessible
			STATUS current
			DESCRIPTION
				"Description."
			INDEX { hwStorageEnclosureSN }
			::= { hwStorageEnclosureTable 1 }

		
		HwStorageEnclosureEntry ::=
			SEQUENCE { 
				hwStorageEnclosureIfIndex
					Unsigned32,
				hwStorageEnclosureSN
					OCTET STRING,
				hwStorageEnclosureID
					Unsigned32,
				hwStorageEnclosureType
					INTEGER,
				hwStorageEnclosureStatus
					INTEGER
			 }

		hwStorageEnclosureIfIndex OBJECT-TYPE
			SYNTAX Unsigned32
			MAX-ACCESS read-only
			STATUS current
			DESCRIPTION
				"Description."
			::= { hwStorageEnclosureEntry 1 }

		
		hwStorageEnclosureSN OBJECT-TYPE
			SYNTAX OCTET STRING (SIZE (0..64))
			MAX-ACCESS read-only
			STATUS current
			DESCRIPTION
				"Description."
			::= { hwStorageEnclosureEntry 2 }

		
		hwStorageEnclosureID OBJECT-TYPE
			SYNTAX Unsigned32
			MAX-ACCESS read-write
			STATUS current
			DESCRIPTION
				"Description."
			::= { hwStorageEnclosureEntry 3 }

		
		hwStorageEnclosureType OBJECT-TYPE
			SYNTAX INTEGER
				{
				expansion(0),
				controller(1)
				}
			MAX-ACCESS read-only
			STATUS current
			DESCRIPTION
				"Description."
			::= { hwStorageEnclosureEntry 4 }

		
		hwStorageEnclosureStatus OBJECT-TYPE
			SYNTAX INTEGER
				{
				nline(0),
				offline(2)
				}
			MAX-ACCESS read-only
			STATUS current
			DESCRIPTION
				"Description."
			::= { hwStorageEnclosureEntry 5 }

		
		hwStorageControllerBoardTable OBJECT-TYPE
			SYNTAX SEQUENCE OF HwStorageControllerBoardEntry
			MAX-ACCESS not-accessible
			STATUS current
			DESCRIPTION
				"Description."
			::= { hwStoragePhysicalModule 3 }

		
		hwStorageControllerBoardEntry OBJECT-TYPE
			SYNTAX HwStorageControllerBoardEntry
			MAX-ACCESS not-accessible
			STATUS current
			DESCRIPTION
				"Description."
			INDEX { hwStorageControllerBoardIfIndex }
			::= { hwStorageControllerBoardTable 1 }

		
		HwStorageControllerBoardEntry ::=
			SEQUENCE { 
				hwStorageControllerBoardIfIndex
					Unsigned32,
				hwStorageControllerBoardEnclosureIfIndex
					Unsigned32,
				hwStorageControllerBoardID
					Unsigned32,
				hwStorageControllerBoardIsPrimary
					INTEGER,
				hwStorageControllerBoardCacheCapacity
					Unsigned32,
				hwStorageControllerBoardCacheHighWater
					Integer32,
				hwStorageControllerBoardCacheLowWater
					Integer32,
				hwStorageControllerBoardStatus
					INTEGER,
				hwStorageControllerBoardSoftwareVersion
					OCTET STRING,
				hwStorageControllerBoardLogicalVersion
					OCTET STRING,
				hwStorageControllerBoardSESVersion
					OCTET STRING,
				hwStorageControllerBoardPCBVersion
					OCTET STRING
			 }

		hwStorageControllerBoardIfIndex OBJECT-TYPE
			SYNTAX Unsigned32
			MAX-ACCESS read-only
			STATUS current
			DESCRIPTION
				"Description."
			::= { hwStorageControllerBoardEntry 1 }

		
		hwStorageControllerBoardEnclosureIfIndex OBJECT-TYPE
			SYNTAX Unsigned32
			MAX-ACCESS read-only
			STATUS current
			DESCRIPTION
				"Description."
			::= { hwStorageControllerBoardEntry 2 }

		
		hwStorageControllerBoardID OBJECT-TYPE
			SYNTAX Unsigned32
			MAX-ACCESS read-only
			STATUS current
			DESCRIPTION
				"controller id"
			::= { hwStorageControllerBoardEntry 3 }

		
		hwStorageControllerBoardIsPrimary OBJECT-TYPE
			SYNTAX INTEGER
				{
				secondary(0),
				primary(1)
				}
			MAX-ACCESS read-only
			STATUS current
			DESCRIPTION
				"Description."
			::= { hwStorageControllerBoardEntry 4 }

		
		hwStorageControllerBoardCacheCapacity OBJECT-TYPE
			SYNTAX Unsigned32
			MAX-ACCESS read-only
			STATUS current
			DESCRIPTION
				"units: MB"
			::= { hwStorageControllerBoardEntry 5 }

		
		hwStorageControllerBoardCacheHighWater OBJECT-TYPE
			SYNTAX Integer32 (0..100)
			MAX-ACCESS read-write
			STATUS current
			DESCRIPTION
				"Description."
			::= { hwStorageControllerBoardEntry 6 }

		
		hwStorageControllerBoardCacheLowWater OBJECT-TYPE
			SYNTAX Integer32 (0..100)
			MAX-ACCESS read-write
			STATUS current
			DESCRIPTION
				"Description."
			::= { hwStorageControllerBoardEntry 7 }

		
		hwStorageControllerBoardStatus OBJECT-TYPE
			SYNTAX INTEGER
				{
				offline(0),
				normal(1),
				abnormal(2)
				}
			MAX-ACCESS read-only
			STATUS current
			DESCRIPTION
				"Description."
			::= { hwStorageControllerBoardEntry 8 }

		
		hwStorageControllerBoardSoftwareVersion OBJECT-TYPE
			SYNTAX OCTET STRING
			MAX-ACCESS read-only
			STATUS current
			DESCRIPTION
				"Description."
			::= { hwStorageControllerBoardEntry 9 }

		
		hwStorageControllerBoardLogicalVersion OBJECT-TYPE
			SYNTAX OCTET STRING
			MAX-ACCESS read-only
			STATUS current
			DESCRIPTION
				"Description."
			::= { hwStorageControllerBoardEntry 10 }

		
		hwStorageControllerBoardSESVersion OBJECT-TYPE
			SYNTAX OCTET STRING
			MAX-ACCESS read-only
			STATUS current
			DESCRIPTION
				"Description."
			::= { hwStorageControllerBoardEntry 11 }

		
		hwStorageControllerBoardPCBVersion OBJECT-TYPE
			SYNTAX OCTET STRING
			MAX-ACCESS read-only
			STATUS current
			DESCRIPTION
				"Description."
			::= { hwStorageControllerBoardEntry 12 }

		
		hwStorageInterfaceBoardTable OBJECT-TYPE
			SYNTAX SEQUENCE OF HwStorageInterfaceBoardEntry
			MAX-ACCESS not-accessible
			STATUS current
			DESCRIPTION
				"Description."
			::= { hwStoragePhysicalModule 4 }

		
		hwStorageInterfaceBoardEntry OBJECT-TYPE
			SYNTAX HwStorageInterfaceBoardEntry
			MAX-ACCESS not-accessible
			STATUS current
			DESCRIPTION
				"Description."
			INDEX { hwStorageInterfaceBoardIfIndex }
			::= { hwStorageInterfaceBoardTable 1 }

		
		HwStorageInterfaceBoardEntry ::=
			SEQUENCE { 
				hwStorageInterfaceBoardIfIndex
					Unsigned32,
				hwStorageInterfaceBoardEnclosureIfIndex
					Unsigned32,
				hwStorageInterfaceBoardID
					Unsigned32,
				hwStorageInterfaceBoardController
					Unsigned32,
				hwStorageInterfaceBoardType
					Unsigned32,
				hwStorageInterfaceBoardStatus
					INTEGER,
				hwStorageInterfaceBoardPCBVersion
					OCTET STRING
			 }

		hwStorageInterfaceBoardIfIndex OBJECT-TYPE
			SYNTAX Unsigned32
			MAX-ACCESS read-only
			STATUS current
			DESCRIPTION
				"Description."
			::= { hwStorageInterfaceBoardEntry 1 }

		
		hwStorageInterfaceBoardEnclosureIfIndex OBJECT-TYPE
			SYNTAX Unsigned32
			MAX-ACCESS read-only
			STATUS current
			DESCRIPTION
				"Description."
			::= { hwStorageInterfaceBoardEntry 2 }

		
		hwStorageInterfaceBoardID OBJECT-TYPE
			SYNTAX Unsigned32
			MAX-ACCESS read-only
			STATUS current
			DESCRIPTION
				"Description."
			::= { hwStorageInterfaceBoardEntry 3 }

		
		hwStorageInterfaceBoardController OBJECT-TYPE
			SYNTAX Unsigned32
			MAX-ACCESS read-only
			STATUS current
			DESCRIPTION
				"Description."
			::= { hwStorageInterfaceBoardEntry 4 }

		
		hwStorageInterfaceBoardType OBJECT-TYPE
			SYNTAX Unsigned32
			MAX-ACCESS read-only
			STATUS current
			DESCRIPTION
				"Description."
			::= { hwStorageInterfaceBoardEntry 5 }

		
		hwStorageInterfaceBoardStatus OBJECT-TYPE
			SYNTAX INTEGER
				{
				abnormal(0),
				normal(1),
				fault(2),
				unactivated(3),
				poweringon(4),
				poweringoff(5),
				poweroff(6)
				}
			MAX-ACCESS read-only
			STATUS current
			DESCRIPTION
				"Description."
			::= { hwStorageInterfaceBoardEntry 6 }

		
		hwStorageInterfaceBoardPCBVersion OBJECT-TYPE
			SYNTAX OCTET STRING
			MAX-ACCESS read-only
			STATUS current
			DESCRIPTION
				"Description."
			::= { hwStorageInterfaceBoardEntry 7 }

		
		hwStorageExpansionBoardTable OBJECT-TYPE
			SYNTAX SEQUENCE OF HwStorageExpansionBoardEntry
			MAX-ACCESS not-accessible
			STATUS current
			DESCRIPTION
				"Description."
			::= { hwStoragePhysicalModule 5 }

		
		hwStorageExpansionBoardEntry OBJECT-TYPE
			SYNTAX HwStorageExpansionBoardEntry
			MAX-ACCESS not-accessible
			STATUS current
			DESCRIPTION
				"Description."
			INDEX { hwStorageExpansionBoardIfIndex }
			::= { hwStorageExpansionBoardTable 1 }

		
		HwStorageExpansionBoardEntry ::=
			SEQUENCE { 
				hwStorageExpansionBoardIfIndex
					Unsigned32,
				hwStorageExpansionBoardEnclosureIfIndex
					Unsigned32,
				hwStorageExpansionBoardType
					INTEGER,
				hwStorageExpansionBoardStatus
					INTEGER,
				hwStorageExpansionBoardLogicVersion
					OCTET STRING,
				hwStorageExpansionBoardSESVersion
					OCTET STRING,
				hwStorageExpansionBoardPCBVersion
					OCTET STRING
			 }

		hwStorageExpansionBoardIfIndex OBJECT-TYPE
			SYNTAX Unsigned32
			MAX-ACCESS read-only
			STATUS current
			DESCRIPTION
				"Description."
			::= { hwStorageExpansionBoardEntry 1 }

		
		hwStorageExpansionBoardEnclosureIfIndex OBJECT-TYPE
			SYNTAX Unsigned32
			MAX-ACCESS read-only
			STATUS current
			DESCRIPTION
				"Description."
			::= { hwStorageExpansionBoardEntry 2 }

		
		hwStorageExpansionBoardType OBJECT-TYPE
			SYNTAX INTEGER
				{
				sasexpansion(0),
				fcexpansion(1)
				}
			MAX-ACCESS read-only
			STATUS current
			DESCRIPTION
				"Description."
			::= { hwStorageExpansionBoardEntry 3 }

		
		hwStorageExpansionBoardStatus OBJECT-TYPE
			SYNTAX INTEGER
				{
				abnormal(0),
				normal(1)
				}
			MAX-ACCESS read-only
			STATUS current
			DESCRIPTION
				"Description."
			::= { hwStorageExpansionBoardEntry 4 }

		
		hwStorageExpansionBoardLogicVersion OBJECT-TYPE
			SYNTAX OCTET STRING
			MAX-ACCESS read-only
			STATUS current
			DESCRIPTION
				"Description."
			::= { hwStorageExpansionBoardEntry 5 }

		
		hwStorageExpansionBoardSESVersion OBJECT-TYPE
			SYNTAX OCTET STRING
			MAX-ACCESS read-only
			STATUS current
			DESCRIPTION
				"Description."
			::= { hwStorageExpansionBoardEntry 6 }

		
		hwStorageExpansionBoardPCBVersion OBJECT-TYPE
			SYNTAX OCTET STRING
			MAX-ACCESS read-only
			STATUS current
			DESCRIPTION
				"Description."
			::= { hwStorageExpansionBoardEntry 7 }

		
		hwStorageMGMTPortTable OBJECT-TYPE
			SYNTAX SEQUENCE OF HwStorageMGMTPortEntry
			MAX-ACCESS not-accessible
			STATUS current
			DESCRIPTION
				"Description."
			::= { hwStoragePhysicalModule 6 }

		
		hwStorageMGMTPortEntry OBJECT-TYPE
			SYNTAX HwStorageMGMTPortEntry
			MAX-ACCESS not-accessible
			STATUS current
			DESCRIPTION
				"Description."
			INDEX { hwStorageMGMTPortIfIndex }
			::= { hwStorageMGMTPortTable 1 }

		
		HwStorageMGMTPortEntry ::=
			SEQUENCE { 
				hwStorageMGMTPortIfIndex
					Unsigned32,
				hwStorageMGMTPortBoardIfIndex
					Unsigned32,
				hwStorageMGMTPortIPAddress
					IpAddress,
				hwStorageMGMTPortNetMask
					IpAddress,
				hwStorageMGMTPortGateWay
					IpAddress,
				hwStorageMGMTPortPhysAddress
					OCTET STRING
			 }

		hwStorageMGMTPortIfIndex OBJECT-TYPE
			SYNTAX Unsigned32
			MAX-ACCESS read-only
			STATUS current
			DESCRIPTION
				"Description."
			::= { hwStorageMGMTPortEntry 1 }

		
		hwStorageMGMTPortBoardIfIndex OBJECT-TYPE
			SYNTAX Unsigned32
			MAX-ACCESS read-only
			STATUS current
			DESCRIPTION
				"Description."
			::= { hwStorageMGMTPortEntry 2 }

		
		hwStorageMGMTPortIPAddress OBJECT-TYPE
			SYNTAX IpAddress
			MAX-ACCESS read-write
			STATUS current
			DESCRIPTION
				"Description."
			::= { hwStorageMGMTPortEntry 3 }

		
		hwStorageMGMTPortNetMask OBJECT-TYPE
			SYNTAX IpAddress
			MAX-ACCESS read-write
			STATUS current
			DESCRIPTION
				"Description."
			::= { hwStorageMGMTPortEntry 4 }

		
		hwStorageMGMTPortGateWay OBJECT-TYPE
			SYNTAX IpAddress
			MAX-ACCESS read-write
			STATUS current
			DESCRIPTION
				"Description."
			::= { hwStorageMGMTPortEntry 5 }

		
		hwStorageMGMTPortPhysAddress OBJECT-TYPE
			SYNTAX OCTET STRING
			MAX-ACCESS read-only
			STATUS current
			DESCRIPTION
				"mac address"
			::= { hwStorageMGMTPortEntry 6 }

		
		hwStorageFCPortTable OBJECT-TYPE
			SYNTAX SEQUENCE OF HwStorageFCPortEntry
			MAX-ACCESS not-accessible
			STATUS current
			DESCRIPTION
				"Description."
			::= { hwStoragePhysicalModule 7 }

		
		hwStorageFCPortEntry OBJECT-TYPE
			SYNTAX HwStorageFCPortEntry
			MAX-ACCESS not-accessible
			STATUS current
			DESCRIPTION
				"Description."
			INDEX { hwStorageFCPortIfIndex }
			::= { hwStorageFCPortTable 1 }

		
		HwStorageFCPortEntry ::=
			SEQUENCE { 
				hwStorageFCPortIfIndex
					Unsigned32,
				hwStorageFCPortBoardIfIndex
					Unsigned32,
				hwStorageFCPortID
					Unsigned32,
				hwStorageFCPortStatus
					INTEGER,
				hwStorageFCPortConfigRate
					INTEGER,
				hwStorageFCPortMode
					INTEGER,
				hwStorageFCPortWWN
					OCTET STRING,
				hwStorageFCPortLogicType
					INTEGER,
				hwStorageFCPortSpeedRate
					INTEGER
			 }

		hwStorageFCPortIfIndex OBJECT-TYPE
			SYNTAX Unsigned32
			MAX-ACCESS read-only
			STATUS current
			DESCRIPTION
				"Description."
			::= { hwStorageFCPortEntry 1 }

		
		hwStorageFCPortBoardIfIndex OBJECT-TYPE
			SYNTAX Unsigned32
			MAX-ACCESS read-only
			STATUS current
			DESCRIPTION
				"owning board ifindex"
			::= { hwStorageFCPortEntry 2 }

		
		hwStorageFCPortID OBJECT-TYPE
			SYNTAX Unsigned32
			MAX-ACCESS read-only
			STATUS current
			DESCRIPTION
				"Description."
			::= { hwStorageFCPortEntry 3 }

		
		hwStorageFCPortStatus OBJECT-TYPE
			SYNTAX INTEGER
				{
				linkdown(0),
				linkup(1),
				fault(2)
				}
			MAX-ACCESS read-only
			STATUS current
			DESCRIPTION
				"Description."
			::= { hwStorageFCPortEntry 4 }

		
		hwStorageFCPortConfigRate OBJECT-TYPE
			SYNTAX INTEGER
				{
				auto(0),
				gbps1(1),
				gbps2(2),
				gbps4(4),
				gbps8(8)
				}
			MAX-ACCESS read-write
			STATUS current
			DESCRIPTION
				"Description."
			::= { hwStorageFCPortEntry 5 }

		
		hwStorageFCPortMode OBJECT-TYPE
			SYNTAX INTEGER
				{
				fabric(1),
				publicloop(2),
				pointtopoint(3)
				}
			MAX-ACCESS read-write
			STATUS current
			DESCRIPTION
				"Description."
			::= { hwStorageFCPortEntry 6 }

		
		hwStorageFCPortWWN OBJECT-TYPE
			SYNTAX OCTET STRING
			MAX-ACCESS read-only
			STATUS current
			DESCRIPTION
				"Description."
			::= { hwStorageFCPortEntry 7 }

		
		hwStorageFCPortLogicType OBJECT-TYPE
			SYNTAX INTEGER
				{
				service(1),
				ibc(2),
				ibs(3),
				expansion(4),
				management(5),
				upsmanagement(6),
				maintenance(8)
				}
			MAX-ACCESS read-only
			STATUS current
			DESCRIPTION
				"Description."
			::= { hwStorageFCPortEntry 8 }

		
		hwStorageFCPortSpeedRate OBJECT-TYPE
			SYNTAX INTEGER
				{
				auto(0),
				gbps1(1),
				gbps2(2),
				gbps4(4),
				gbps8(8)
				}
			MAX-ACCESS read-only
			STATUS current
			DESCRIPTION
				"Description."
			::= { hwStorageFCPortEntry 9 }

		
		hwStorageSASPortTable OBJECT-TYPE
			SYNTAX SEQUENCE OF HwStorageSASPortEntry
			MAX-ACCESS not-accessible
			STATUS current
			DESCRIPTION
				"Description."
			::= { hwStoragePhysicalModule 8 }

		
		hwStorageSASPortEntry OBJECT-TYPE
			SYNTAX HwStorageSASPortEntry
			MAX-ACCESS not-accessible
			STATUS current
			DESCRIPTION
				"Description."
			INDEX { hwStorageSASPortIfIndex }
			::= { hwStorageSASPortTable 1 }

		
		HwStorageSASPortEntry ::=
			SEQUENCE { 
				hwStorageSASPortIfIndex
					Unsigned32,
				hwStorageSASPortBoardIfIndex
					Unsigned32,
				hwStorageSASPortID
					Unsigned32,
				hwStorageSASPortStatus
					INTEGER,
				hwStorageSASPortConfigRate
					INTEGER,
				hwStorageSASPortWWN
					OCTET STRING,
				hwStorageSASPortLogicType
					INTEGER,
				hwStorageSASPortSpeedRate
					INTEGER
			 }

		hwStorageSASPortIfIndex OBJECT-TYPE
			SYNTAX Unsigned32
			MAX-ACCESS read-only
			STATUS current
			DESCRIPTION
				"Description."
			::= { hwStorageSASPortEntry 1 }

		
		hwStorageSASPortBoardIfIndex OBJECT-TYPE
			SYNTAX Unsigned32
			MAX-ACCESS read-only
			STATUS current
			DESCRIPTION
				"owning board ifindex"
			::= { hwStorageSASPortEntry 2 }

		
		hwStorageSASPortID OBJECT-TYPE
			SYNTAX Unsigned32
			MAX-ACCESS read-only
			STATUS current
			DESCRIPTION
				"Description."
			::= { hwStorageSASPortEntry 3 }

		
		hwStorageSASPortStatus OBJECT-TYPE
			SYNTAX INTEGER
				{
				linkdown(0),
				linkup(1),
				fault(2)
				}
			MAX-ACCESS read-only
			STATUS current
			DESCRIPTION
				"Description."
			::= { hwStorageSASPortEntry 4 }

		
		hwStorageSASPortConfigRate OBJECT-TYPE
			SYNTAX INTEGER
				{
				gbps15(1500),
				gbps30(3000),
				gbps60(6000)
				}
			MAX-ACCESS read-only
			STATUS current
			DESCRIPTION
				"Description."
			::= { hwStorageSASPortEntry 5 }

		
		hwStorageSASPortWWN OBJECT-TYPE
			SYNTAX OCTET STRING
			MAX-ACCESS read-only
			STATUS current
			DESCRIPTION
				"Description."
			::= { hwStorageSASPortEntry 6 }

		
		hwStorageSASPortLogicType OBJECT-TYPE
			SYNTAX INTEGER
				{
				service(1),
				ibc(2),
				ibs(3),
				expansion(4),
				management(5),
				upsmanagement(6),
				maintenance(8)
				}
			MAX-ACCESS read-only
			STATUS current
			DESCRIPTION
				"Description."
			::= { hwStorageSASPortEntry 7 }

		
		hwStorageSASPortSpeedRate OBJECT-TYPE
			SYNTAX INTEGER
				{
				gbps15(1500),
				gbps30(3000),
				gbps60(6000)
				}
			MAX-ACCESS read-only
			STATUS current
			DESCRIPTION
				"Description."
			::= { hwStorageSASPortEntry 8 }

		
		hwStorageISCSIPortTable OBJECT-TYPE
			SYNTAX SEQUENCE OF HwStorageISCSIPortEntry
			MAX-ACCESS not-accessible
			STATUS current
			DESCRIPTION
				"Description."
			::= { hwStoragePhysicalModule 9 }

		
		hwStorageISCSIPortEntry OBJECT-TYPE
			SYNTAX HwStorageISCSIPortEntry
			MAX-ACCESS not-accessible
			STATUS current
			DESCRIPTION
				"Description."
			INDEX { hwStorageISCSIPortIfIndex }
			::= { hwStorageISCSIPortTable 1 }

		
		HwStorageISCSIPortEntry ::=
			SEQUENCE { 
				hwStorageISCSIPortIfIndex
					Unsigned32,
				hwStorageISCSIPortBoardIfIndex
					Unsigned32,
				hwStorageISCSIPortID
					Unsigned32,
				hwStorageISCSIPortStatus
					INTEGER,
				hwStorageISCSIPortIP
					IpAddress,
				hwStorageISCSIPortNetMask
					IpAddress,
				hwStorageISCSIPortBindMode
					Integer32,
				hwStorageISCSIPortLogicType
					INTEGER
			 }

		hwStorageISCSIPortIfIndex OBJECT-TYPE
			SYNTAX Unsigned32
			MAX-ACCESS read-only
			STATUS current
			DESCRIPTION
				"Description."
			::= { hwStorageISCSIPortEntry 1 }

		
		hwStorageISCSIPortBoardIfIndex OBJECT-TYPE
			SYNTAX Unsigned32
			MAX-ACCESS read-only
			STATUS current
			DESCRIPTION
				"owning board ifindex"
			::= { hwStorageISCSIPortEntry 2 }

		
		hwStorageISCSIPortID OBJECT-TYPE
			SYNTAX Unsigned32
			MAX-ACCESS read-only
			STATUS current
			DESCRIPTION
				"Description."
			::= { hwStorageISCSIPortEntry 3 }

		
		hwStorageISCSIPortStatus OBJECT-TYPE
			SYNTAX INTEGER
				{
				linkdown(0),
				linkup(1),
				fault(2)
				}
			MAX-ACCESS read-only
			STATUS current
			DESCRIPTION
				"Description."
			::= { hwStorageISCSIPortEntry 4 }

		
		hwStorageISCSIPortIP OBJECT-TYPE
			SYNTAX IpAddress
			MAX-ACCESS read-write
			STATUS current
			DESCRIPTION
				"Description."
			::= { hwStorageISCSIPortEntry 5 }

		
		hwStorageISCSIPortNetMask OBJECT-TYPE
			SYNTAX IpAddress
			MAX-ACCESS read-write
			STATUS current
			DESCRIPTION
				"Description."
			::= { hwStorageISCSIPortEntry 6 }

		
		hwStorageISCSIPortBindMode OBJECT-TYPE
			SYNTAX Integer32
			MAX-ACCESS read-only
			STATUS current
			DESCRIPTION
				"Description."
			::= { hwStorageISCSIPortEntry 7 }

		
		hwStorageISCSIPortLogicType OBJECT-TYPE
			SYNTAX INTEGER
				{
				service(1),
				ibc(2),
				ibs(3),
				expansion(4),
				management(5),
				upsmanagement(6),
				maintenance(8)
				}
			MAX-ACCESS read-only
			STATUS current
			DESCRIPTION
				"Description."
			::= { hwStorageISCSIPortEntry 8 }

		
		hwStorageReplicationLinkTable OBJECT-TYPE
			SYNTAX SEQUENCE OF HwStorageReplicationLinkEntry
			MAX-ACCESS not-accessible
			STATUS current
			DESCRIPTION
				"Description."
			::= { hwStoragePhysicalModule 10 }

		
		hwStorageReplicationLinkEntry OBJECT-TYPE
			SYNTAX HwStorageReplicationLinkEntry
			MAX-ACCESS not-accessible
			STATUS current
			DESCRIPTION
				"Description."
			INDEX { hwStorageReplicationLinkID }
			::= { hwStorageReplicationLinkTable 1 }

		
		HwStorageReplicationLinkEntry ::=
			SEQUENCE { 
				hwStorageReplicationLinkID
					Unsigned32,
				hwStorageReplicationLinkArrayID
					Unsigned32,
				hwStorageReplicationLinkType
					INTEGER,
				hwStorageReplicationLinkStatus
					INTEGER,
				hwStorageReplicationLinkUsed
					INTEGER,
				hwStorageReplicationLinkRowStatus
					RowStatus
			 }

		hwStorageReplicationLinkID OBJECT-TYPE
			SYNTAX Unsigned32
			MAX-ACCESS read-only
			STATUS current
			DESCRIPTION
				"Description."
			::= { hwStorageReplicationLinkEntry 1 }

		
		hwStorageReplicationLinkArrayID OBJECT-TYPE
			SYNTAX Unsigned32
			MAX-ACCESS read-only
			STATUS current
			DESCRIPTION
				"Description."
			::= { hwStorageReplicationLinkEntry 2 }

		
		hwStorageReplicationLinkType OBJECT-TYPE
			SYNTAX INTEGER
				{
				fc(1),
				iscsi(2)
				}
			MAX-ACCESS read-only
			STATUS current
			DESCRIPTION
				"Description."
			::= { hwStorageReplicationLinkEntry 3 }

		
		hwStorageReplicationLinkStatus OBJECT-TYPE
			SYNTAX INTEGER
				{
				connected(1),
				unconnected(2)
				}
			MAX-ACCESS read-only
			STATUS current
			DESCRIPTION
				"Description."
			::= { hwStorageReplicationLinkEntry 4 }

		
		hwStorageReplicationLinkUsed OBJECT-TYPE
			SYNTAX INTEGER
				{
				no(0),
				yes(1)
				}
			MAX-ACCESS read-only
			STATUS current
			DESCRIPTION
				"Description."
			::= { hwStorageReplicationLinkEntry 5 }

		
		hwStorageReplicationLinkRowStatus OBJECT-TYPE
			SYNTAX RowStatus
			MAX-ACCESS read-write
			STATUS current
			DESCRIPTION
				"Description."
			::= { hwStorageReplicationLinkEntry 50 }

		
		hwStorageFrontEndHostPortTable OBJECT-TYPE
			SYNTAX SEQUENCE OF HwStorageFrontEndHostPortEntry
			MAX-ACCESS not-accessible
			STATUS current
			DESCRIPTION
				"Front-End Host Port"
			::= { hwStoragePhysicalModule 11 }

		
		hwStorageFrontEndHostPortEntry OBJECT-TYPE
			SYNTAX HwStorageFrontEndHostPortEntry
			MAX-ACCESS not-accessible
			STATUS current
			DESCRIPTION
				"Description."
			INDEX { hwStorageFrontEndHostPortIfIndex }
			::= { hwStorageFrontEndHostPortTable 1 }

		
		HwStorageFrontEndHostPortEntry ::=
			SEQUENCE { 
				hwStorageFrontEndHostPortIfIndex
					Unsigned32,
				hwStorageFrontEndHostPortType
					INTEGER,
				hwStorageFrontEndHostPortStatus
					INTEGER,
				hwStorageFrontEndHostPortPhysAddress
					OCTET STRING,
				hwStorageFrontEndHostPortDescription
					OCTET STRING
			 }

		hwStorageFrontEndHostPortIfIndex OBJECT-TYPE
			SYNTAX Unsigned32
			MAX-ACCESS read-only
			STATUS current
			DESCRIPTION
				"A unique value for each front-end port."
			::= { hwStorageFrontEndHostPortEntry 1 }

		
		hwStorageFrontEndHostPortType OBJECT-TYPE
			SYNTAX INTEGER
				{
				sas(0),
				fc(1),
				iscsi(5)
				}
			MAX-ACCESS read-only
			STATUS current
			DESCRIPTION
				"Description."
			::= { hwStorageFrontEndHostPortEntry 2 }

		
		hwStorageFrontEndHostPortStatus OBJECT-TYPE
			SYNTAX INTEGER
				{
				linkdown(0),
				linkup(1),
				fault(2),
				unknown(3)
				}
			MAX-ACCESS read-only
			STATUS current
			DESCRIPTION
				"Description."
			::= { hwStorageFrontEndHostPortEntry 3 }

		
		hwStorageFrontEndHostPortPhysAddress OBJECT-TYPE
			SYNTAX OCTET STRING
			MAX-ACCESS read-only
			STATUS current
			DESCRIPTION
				"Description."
			::= { hwStorageFrontEndHostPortEntry 4 }

		
		hwStorageFrontEndHostPortDescription OBJECT-TYPE
			SYNTAX OCTET STRING
			MAX-ACCESS read-only
			STATUS current
			DESCRIPTION
				"Description."
			::= { hwStorageFrontEndHostPortEntry 5 }

		
		hwStorageControllerTable OBJECT-TYPE
			SYNTAX SEQUENCE OF HwStorageControllerEntry
			MAX-ACCESS not-accessible
			STATUS current
			DESCRIPTION
				"Description."
			::= { hwStoragePhysicalModule 12 }

		
		hwStorageControllerEntry OBJECT-TYPE
			SYNTAX HwStorageControllerEntry
			MAX-ACCESS not-accessible
			STATUS current
			DESCRIPTION
				"Description."
			INDEX { hwStorageControllerID }
			::= { hwStorageControllerTable 1 }

		
		HwStorageControllerEntry ::=
			SEQUENCE { 
				hwStorageControllerID
					Unsigned32,
				hwStorageControllerName
					OCTET STRING,
				hwStorageControllerLocation
					OCTET STRING,
				hwStorageControllerHealthStatus
					INTEGER,
				hwStorageControllerRunningStatus
					INTEGER,
				hwStorageControllerSoftVer
					OCTET STRING,
				hwStorageControllerTemperature
					Integer32,
				hwStorageControllerIsMaster
					Unsigned32,
				hwStorageControllerELabel
					OCTET STRING,
				hwStorageControllerPCBVer
					OCTET STRING,
				hwStorageControllerBMCVer
					OCTET STRING,
				hwStorageControllerLogicVer
					OCTET STRING,
				hwStorageControllerBIOSVer
					OCTET STRING,
				hwStorageControllerMemorySize
					Unsigned32,
				hwStorageControllerCPUInfo
					OCTET STRING,
				hwStorageControllerVoltage
					Unsigned32
			 }

		hwStorageControllerID OBJECT-TYPE
			SYNTAX Unsigned32
			MAX-ACCESS read-only
			STATUS current
			DESCRIPTION
				"Controller ID"
			::= { hwStorageControllerEntry 1 }

		
		hwStorageControllerName OBJECT-TYPE
			SYNTAX OCTET STRING
			MAX-ACCESS read-only
			STATUS current
			DESCRIPTION
				"Contrller Name"
			::= { hwStorageControllerEntry 2 }

		
		hwStorageControllerLocation OBJECT-TYPE
			SYNTAX OCTET STRING
			MAX-ACCESS read-only
			STATUS current
			DESCRIPTION
				"the location of the Controller"
			::= { hwStorageControllerEntry 3 }

		
		hwStorageControllerHealthStatus OBJECT-TYPE
			SYNTAX INTEGER
				{
				normal(1),
				fault(2),
				preFail(3),
				partiallyBroken(4),
				degraded(5),
				badSectorsFound(6),
				bitErrorsFound(7),
				consistent(8),
				inconsistent(9),
				busy(10),
				noInput(11),
				lowBattery(12),
				singleLinkFault(13)
				}
			MAX-ACCESS read-only
			STATUS current
			DESCRIPTION
				"health status of the controller"
			::= { hwStorageControllerEntry 4 }

		
		hwStorageControllerRunningStatus OBJECT-TYPE
			SYNTAX INTEGER
				{
				normal(1),
				running(2),
				notRunning(3),
				notExisted(4),
				sleepInHighTemperature(5),
				starting(6),
				powerFailureProtecting(7),
				spinDown(8),
				started(9),
				linkUp(10),
				linkDown(11),
				poweringOn(12),
				poweredOff(13),
				precopy(14),
				copyback(15),
				reconstruction(16),
				expansion(17),
				unformatted(18),
				formatting(19),
				unmapped(20),
				initialSynchronizing(21),
				consistent(22),
				synchronizing(23),
				synchronized(24),
				unsynchronized(25),
				splited(26),
				online(27),
				offline(28),
				locked(29),
				enabled(30),
				disabled(31),
				balancing(32),
				toBeRecoverd(33),
				interrupted(34),
				invalid(35),
				notStart(36),
				queuing(37),
				stopped(38),
				copying(39),
				completed(40),
				paused(41),
				reverseSynchronizing(42),
				activated(43),
				restore(44),
				inactive(45),
				idle(46),
				poweringOff(47),
				charging(48),
				chargingCompleted(49),
				discharging(50),
				upgrading(51),
				runningNormal(63),
				runningFail(64)
				}
			MAX-ACCESS read-only
			STATUS current
			DESCRIPTION
				"running status of the controller"
			::= { hwStorageControllerEntry 5 }

		
		hwStorageControllerSoftVer OBJECT-TYPE
			SYNTAX OCTET STRING
			MAX-ACCESS read-only
			STATUS current
			DESCRIPTION
				"firmware version"
			::= { hwStorageControllerEntry 6 }

		
		hwStorageControllerTemperature OBJECT-TYPE
			SYNTAX Integer32
			MAX-ACCESS read-only
			STATUS current
			DESCRIPTION
				"controller temperature"
			::= { hwStorageControllerEntry 7 }

		
		hwStorageControllerIsMaster OBJECT-TYPE
			SYNTAX Unsigned32
			MAX-ACCESS read-only
			STATUS current
			DESCRIPTION
				"is primary controller"
			::= { hwStorageControllerEntry 8 }

		
		hwStorageControllerELabel OBJECT-TYPE
			SYNTAX OCTET STRING
			MAX-ACCESS read-only
			STATUS current
			DESCRIPTION
				"controller e-lable version"
			::= { hwStorageControllerEntry 9 }

		
		hwStorageControllerPCBVer OBJECT-TYPE
			SYNTAX OCTET STRING
			MAX-ACCESS read-only
			STATUS current
			DESCRIPTION
				"PCB version"
			::= { hwStorageControllerEntry 10 }

		
		hwStorageControllerBMCVer OBJECT-TYPE
			SYNTAX OCTET STRING
			MAX-ACCESS read-only
			STATUS current
			DESCRIPTION
				"BMC versoin"
			::= { hwStorageControllerEntry 11 }

		
		hwStorageControllerLogicVer OBJECT-TYPE
			SYNTAX OCTET STRING
			MAX-ACCESS read-only
			STATUS current
			DESCRIPTION
				"logic version"
			::= { hwStorageControllerEntry 12 }

		
		hwStorageControllerBIOSVer OBJECT-TYPE
			SYNTAX OCTET STRING
			MAX-ACCESS read-only
			STATUS current
			DESCRIPTION
				"BIOS version"
			::= { hwStorageControllerEntry 13 }

		
		hwStorageControllerMemorySize OBJECT-TYPE
			SYNTAX Unsigned32
			MAX-ACCESS read-only
			STATUS current
			DESCRIPTION
				"memory size(M)"
			::= { hwStorageControllerEntry 14 }

		
		hwStorageControllerCPUInfo OBJECT-TYPE
			SYNTAX OCTET STRING
			MAX-ACCESS read-only
			STATUS current
			DESCRIPTION
				"cpu info"
			::= { hwStorageControllerEntry 15 }

		
		hwStorageControllerVoltage OBJECT-TYPE
			SYNTAX Unsigned32
			MAX-ACCESS read-only
			STATUS current
			DESCRIPTION
				"voltage(V) = value/10"
			::= { hwStorageControllerEntry 16 }

		
		hwStorageLogicModule OBJECT IDENTIFIER ::= { hwStorageService 9 }

		
		hwStorageCacheTable OBJECT-TYPE
			SYNTAX SEQUENCE OF HwStorageCacheEntry
			MAX-ACCESS not-accessible
			STATUS current
			DESCRIPTION
				"Description."
			::= { hwStorageLogicModule 1 }

		
		hwStorageCacheEntry OBJECT-TYPE
			SYNTAX HwStorageCacheEntry
			MAX-ACCESS not-accessible
			STATUS current
			DESCRIPTION
				"Description."
			INDEX { hwStorageCacheID }
			::= { hwStorageCacheTable 1 }

		
		HwStorageCacheEntry ::=
			SEQUENCE { 
				hwStorageCacheID
					Unsigned32,
				hwStorageCacheTotalCapacity
					Unsigned32,
				hwStorageCacheHighWaterLevel
					Unsigned32,
				hwStorageCacheLowWaterLevel
					Unsigned32,
				hwStorageCacheRowStatus
					RowStatus
			 }

		hwStorageCacheID OBJECT-TYPE
			SYNTAX Unsigned32
			MAX-ACCESS read-only
			STATUS current
			DESCRIPTION
				"cache ID equal to hwStorageControllerBoardID"
			::= { hwStorageCacheEntry 1 }

		
		hwStorageCacheTotalCapacity OBJECT-TYPE
			SYNTAX Unsigned32
			UNITS "MB"
			MAX-ACCESS read-only
			STATUS current
			DESCRIPTION
				"Description."
			::= { hwStorageCacheEntry 2 }

		
		hwStorageCacheHighWaterLevel OBJECT-TYPE
			SYNTAX Unsigned32
			MAX-ACCESS read-write
			STATUS current
			DESCRIPTION
				"Description."
			::= { hwStorageCacheEntry 3 }

		
		hwStorageCacheLowWaterLevel OBJECT-TYPE
			SYNTAX Unsigned32
			MAX-ACCESS read-write
			STATUS current
			DESCRIPTION
				"Description."
			::= { hwStorageCacheEntry 4 }

		
		hwStorageCacheRowStatus OBJECT-TYPE
			SYNTAX RowStatus
			MAX-ACCESS read-write
			STATUS current
			DESCRIPTION
				"Description."
			::= { hwStorageCacheEntry 5 }

		
		hwStorageLunTable OBJECT-TYPE
			SYNTAX SEQUENCE OF HwStorageLunEntry
			MAX-ACCESS not-accessible
			STATUS current
			DESCRIPTION
				"Description."
			::= { hwStorageLogicModule 4 }

		
		hwStorageLunEntry OBJECT-TYPE
			SYNTAX HwStorageLunEntry
			MAX-ACCESS not-accessible
			STATUS current
			DESCRIPTION
				"Description."
			INDEX { hwStorageLunID }
			::= { hwStorageLunTable 1 }

		
		HwStorageLunEntry ::=
			SEQUENCE { 
				hwStorageLunID
					Unsigned32,
				hwStorageLunName
					OCTET STRING,
				hwStorageLunWWN
					OCTET STRING,
				hwStorageLunOwningRaid
					Unsigned32,
				hwStorageLunCapacity
					Counter64,
				hwStorageLunOwningController
					Unsigned32,
				hwStorageLunStripDepth
					Unsigned32,
				hwStorageLunWriteStrategy
					INTEGER,
				hwStorageLunPrefetchStrategy
					INTEGER,
				hwStorageLunPrefetchValue
					Unsigned32,
				hwStorageLunStatus
					INTEGER,
				hwStorageLunRowStatus
					RowStatus
			 }

		hwStorageLunID OBJECT-TYPE
			SYNTAX Unsigned32
			MAX-ACCESS read-only
			STATUS current
			DESCRIPTION
				"Description."
			::= { hwStorageLunEntry 1 }

		
		hwStorageLunName OBJECT-TYPE
			SYNTAX OCTET STRING
			MAX-ACCESS read-only
			STATUS current
			DESCRIPTION
				"Description."
			::= { hwStorageLunEntry 2 }

		
		hwStorageLunWWN OBJECT-TYPE
			SYNTAX OCTET STRING
			MAX-ACCESS read-only
			STATUS current
			DESCRIPTION
				"Description."
			::= { hwStorageLunEntry 3 }

		
		hwStorageLunOwningRaid OBJECT-TYPE
			SYNTAX Unsigned32
			MAX-ACCESS read-only
			STATUS current
			DESCRIPTION
				"owning raid id"
			::= { hwStorageLunEntry 4 }

		
		hwStorageLunCapacity OBJECT-TYPE
			SYNTAX Counter64
			MAX-ACCESS read-only
			STATUS current
			DESCRIPTION
				"Description."
			::= { hwStorageLunEntry 5 }

		
		hwStorageLunOwningController OBJECT-TYPE
			SYNTAX Unsigned32
			MAX-ACCESS read-only
			STATUS current
			DESCRIPTION
				"owning controller id"
			::= { hwStorageLunEntry 6 }

		
		hwStorageLunStripDepth OBJECT-TYPE
			SYNTAX Unsigned32
			MAX-ACCESS read-only
			STATUS current
			DESCRIPTION
				"units: kb"
			::= { hwStorageLunEntry 7 }

		
		hwStorageLunWriteStrategy OBJECT-TYPE
			SYNTAX INTEGER
				{
				writethrough(1),
				writebacknomirroring(2),
				writebackmirroring(3),
				writebackmandatorynomirroring(4),
				writebackmandatorymirroring(5)
				}
			MAX-ACCESS read-only
			STATUS current
			DESCRIPTION
				"Description."
			::= { hwStorageLunEntry 8 }

		
		hwStorageLunPrefetchStrategy OBJECT-TYPE
			SYNTAX INTEGER
				{
				none(0),
				constant(1),
				variable(2),
				intelligent(3)
				}
			MAX-ACCESS read-only
			STATUS current
			DESCRIPTION
				"Description."
			::= { hwStorageLunEntry 9 }

		
		hwStorageLunPrefetchValue OBJECT-TYPE
			SYNTAX Unsigned32
			MAX-ACCESS read-only
			STATUS current
			DESCRIPTION
				"need set value when hwStorageLunPrefetchStrategy's value is Constant or Variable.
				Constant, range: 0~1024KB
				Variable, range: 0~65535"
			::= { hwStorageLunEntry 10 }

		
		hwStorageLunStatus OBJECT-TYPE
			SYNTAX INTEGER
				{
				normal(1),
				fault(2),
				notformat(3),
				formatting(4)
				}
			MAX-ACCESS read-only
			STATUS current
			DESCRIPTION
				"Description."
			::= { hwStorageLunEntry 11 }

		
		hwStorageLunRowStatus OBJECT-TYPE
			SYNTAX RowStatus
			MAX-ACCESS read-only
			STATUS current
			DESCRIPTION
				"Description."
			::= { hwStorageLunEntry 50 }

		
		hwStorageReplicationPipeTable OBJECT-TYPE
			SYNTAX SEQUENCE OF HwStorageReplicationPipeEntry
			MAX-ACCESS not-accessible
			STATUS current
			DESCRIPTION
				"Description."
			::= { hwStorageLogicModule 5 }

		
		hwStorageReplicationPipeEntry OBJECT-TYPE
			SYNTAX HwStorageReplicationPipeEntry
			MAX-ACCESS not-accessible
			STATUS current
			DESCRIPTION
				"Description."
			INDEX { hwStorageReplicationPipenID }
			::= { hwStorageReplicationPipeTable 1 }

		
		HwStorageReplicationPipeEntry ::=
			SEQUENCE { 
				hwStorageReplicationPipenID
					Unsigned32,
				hwStorageReplicationPipeType
					INTEGER,
				hwStorageReplicationPipeStatus
					INTEGER,
				hwStorageReplicationPipeUsed
					INTEGER,
				hwStorageReplicationPipeMirrorLink
					INTEGER,
				hwStorageReplicationPipeMirrorLinkTimeout
					Unsigned32,
				hwStorageReplicationPipeRemoteArrayID
					Unsigned32,
				hwStorageReplicationPipeRemoteArrayWWN
					OCTET STRING,
				hwStorageReplicationPipeLocalController
					Unsigned32,
				hwStorageReplicationPipeRemoteController
					Unsigned32,
				hwStorageReplicationPipeLocalPort
					Unsigned32,
				hwStorageReplicationPipeRemotePort
					Unsigned32,
				hwStorageReplicationPipeLocalWWPN
					OCTET STRING,
				hwStorageReplicationPipeRemoteWWPN
					OCTET STRING,
				hwStorageReplicationPipeTargetName
					OCTET STRING,
				hwStorageReplicationPipeInitiatorName
					Integer32,
				hwStorageReplicationPipeRowStatus
					RowStatus
			 }

		hwStorageReplicationPipenID OBJECT-TYPE
			SYNTAX Unsigned32
			MAX-ACCESS read-write
			STATUS current
			DESCRIPTION
				"Description."
			::= { hwStorageReplicationPipeEntry 1 }

		
		hwStorageReplicationPipeType OBJECT-TYPE
			SYNTAX INTEGER
				{
				fclink(1),
				iSCSIlink(2)
				}
			MAX-ACCESS read-write
			STATUS current
			DESCRIPTION
				"Description."
			::= { hwStorageReplicationPipeEntry 2 }

		
		hwStorageReplicationPipeStatus OBJECT-TYPE
			SYNTAX INTEGER
				{
				connected(1),
				disconnected(2)
				}
			MAX-ACCESS read-write
			STATUS current
			DESCRIPTION
				"Description."
			::= { hwStorageReplicationPipeEntry 3 }

		
		hwStorageReplicationPipeUsed OBJECT-TYPE
			SYNTAX INTEGER
				{
				false(0),
				true(1)
				}
			MAX-ACCESS read-write
			STATUS current
			DESCRIPTION
				"Description."
			::= { hwStorageReplicationPipeEntry 4 }

		
		hwStorageReplicationPipeMirrorLink OBJECT-TYPE
			SYNTAX INTEGER
				{
				false(0),
				true(1)
				}
			MAX-ACCESS read-write
			STATUS current
			DESCRIPTION
				"Description."
			::= { hwStorageReplicationPipeEntry 5 }

		
		hwStorageReplicationPipeMirrorLinkTimeout OBJECT-TYPE
			SYNTAX Unsigned32
			MAX-ACCESS read-write
			STATUS current
			DESCRIPTION
				"Description."
			::= { hwStorageReplicationPipeEntry 6 }

		
		hwStorageReplicationPipeRemoteArrayID OBJECT-TYPE
			SYNTAX Unsigned32
			MAX-ACCESS read-write
			STATUS current
			DESCRIPTION
				"Description."
			::= { hwStorageReplicationPipeEntry 7 }

		
		hwStorageReplicationPipeRemoteArrayWWN OBJECT-TYPE
			SYNTAX OCTET STRING
			MAX-ACCESS read-write
			STATUS current
			DESCRIPTION
				"Description."
			::= { hwStorageReplicationPipeEntry 8 }

		
		hwStorageReplicationPipeLocalController OBJECT-TYPE
			SYNTAX Unsigned32
			MAX-ACCESS read-write
			STATUS current
			DESCRIPTION
				"local controller id"
			::= { hwStorageReplicationPipeEntry 9 }

		
		hwStorageReplicationPipeRemoteController OBJECT-TYPE
			SYNTAX Unsigned32
			MAX-ACCESS read-write
			STATUS current
			DESCRIPTION
				"remote controller id"
			::= { hwStorageReplicationPipeEntry 10 }

		
		hwStorageReplicationPipeLocalPort OBJECT-TYPE
			SYNTAX Unsigned32
			MAX-ACCESS read-write
			STATUS current
			DESCRIPTION
				"local port id"
			::= { hwStorageReplicationPipeEntry 11 }

		
		hwStorageReplicationPipeRemotePort OBJECT-TYPE
			SYNTAX Unsigned32
			MAX-ACCESS read-write
			STATUS current
			DESCRIPTION
				"remote port id"
			::= { hwStorageReplicationPipeEntry 12 }

		
		hwStorageReplicationPipeLocalWWPN OBJECT-TYPE
			SYNTAX OCTET STRING
			MAX-ACCESS read-write
			STATUS current
			DESCRIPTION
				"Description."
			::= { hwStorageReplicationPipeEntry 13 }

		
		hwStorageReplicationPipeRemoteWWPN OBJECT-TYPE
			SYNTAX OCTET STRING
			MAX-ACCESS read-write
			STATUS current
			DESCRIPTION
				"Description."
			::= { hwStorageReplicationPipeEntry 14 }

		
		hwStorageReplicationPipeTargetName OBJECT-TYPE
			SYNTAX OCTET STRING
			MAX-ACCESS read-write
			STATUS current
			DESCRIPTION
				"Description."
			::= { hwStorageReplicationPipeEntry 15 }

		
		hwStorageReplicationPipeInitiatorName OBJECT-TYPE
			SYNTAX Integer32
			MAX-ACCESS read-write
			STATUS current
			DESCRIPTION
				"Description."
			::= { hwStorageReplicationPipeEntry 16 }

		
		hwStorageReplicationPipeRowStatus OBJECT-TYPE
			SYNTAX RowStatus
			MAX-ACCESS read-write
			STATUS current
			DESCRIPTION
				"Description."
			::= { hwStorageReplicationPipeEntry 50 }

		
		hwStorageNodeTable OBJECT-TYPE
			SYNTAX SEQUENCE OF HwStorageNodeEntry
			MAX-ACCESS not-accessible
			STATUS current
			DESCRIPTION
				"Description."
			::= { hwStorageLogicModule 6 }

		
		hwStorageNodeEntry OBJECT-TYPE
			SYNTAX HwStorageNodeEntry
			MAX-ACCESS not-accessible
			STATUS current
			DESCRIPTION
				"Description."
			INDEX { hwStorageNodeIfIndex }
			::= { hwStorageNodeTable 1 }

		
		HwStorageNodeEntry ::=
			SEQUENCE { 
				hwStorageNodeIfIndex
					Unsigned32,
				hwStorageNodeIPAddress
					IpAddress,
				hwStorageNodeStatus
					Unsigned32,
				hwStorageNodeIsMaster
					Unsigned32,
				hwStorageNodeRowStatus
					RowStatus
			 }

		hwStorageNodeIfIndex OBJECT-TYPE
			SYNTAX Unsigned32
			MAX-ACCESS read-only
			STATUS current
			DESCRIPTION
				"Description."
			::= { hwStorageNodeEntry 1 }

		
		hwStorageNodeIPAddress OBJECT-TYPE
			SYNTAX IpAddress
			MAX-ACCESS read-write
			STATUS current
			DESCRIPTION
				"Description."
			::= { hwStorageNodeEntry 2 }

		
		hwStorageNodeStatus OBJECT-TYPE
			SYNTAX Unsigned32
			MAX-ACCESS read-only
			STATUS current
			DESCRIPTION
				"Description."
			::= { hwStorageNodeEntry 3 }

		
		hwStorageNodeIsMaster OBJECT-TYPE
			SYNTAX Unsigned32
			MAX-ACCESS read-write
			STATUS current
			DESCRIPTION
				"Description."
			::= { hwStorageNodeEntry 4 }

		
		hwStorageNodeRowStatus OBJECT-TYPE
			SYNTAX RowStatus
			MAX-ACCESS read-write
			STATUS current
			DESCRIPTION
				"Description."
			::= { hwStorageNodeEntry 20 }

		
		isoConformance OBJECT IDENTIFIER ::= { iso 6 }

		
		isoGroups OBJECT IDENTIFIER ::= { isoConformance 1 }

		
		currentObjectGroup OBJECT-GROUP
			OBJECTS { portNumber, addrName, addrIP, linkMode, linkWWN, 
				linkIP, linkManagedRelation, deviceWwn, deviceRoom, deviceShelf, 
				deviceSlot, hwStorageEnclosureSN, hwStorageEnclosureID, hwStorageEnclosureType, hwStorageEnclosureStatus, 
				hwStorageControllerBoardIfIndex, hwStorageControllerBoardID, hwStorageControllerBoardIsPrimary, hwStorageControllerBoardCacheCapacity, hwStorageControllerBoardCacheHighWater, 
				hwStorageControllerBoardCacheLowWater, hwStorageControllerBoardStatus, hwStorageControllerBoardSoftwareVersion, hwStorageControllerBoardLogicalVersion, hwStorageControllerBoardSESVersion, 
				hwStorageControllerBoardPCBVersion, hwStorageInterfaceBoardIfIndex, hwStorageInterfaceBoardID, hwStorageInterfaceBoardController, hwStorageInterfaceBoardType, 
				hwStorageInterfaceBoardStatus, hwStorageInterfaceBoardPCBVersion, hwStorageExpansionBoardIfIndex, hwStorageExpansionBoardType, hwStorageExpansionBoardStatus, 
				hwStorageExpansionBoardLogicVersion, hwStorageExpansionBoardSESVersion, hwStorageExpansionBoardPCBVersion, hwStorageMGMTPortIfIndex, hwStorageMGMTPortBoardIfIndex, 
				hwStorageMGMTPortIPAddress, hwStorageMGMTPortNetMask, hwStorageMGMTPortGateWay, hwStorageMGMTPortPhysAddress, hwStorageFCPortIfIndex, 
				hwStorageFCPortBoardIfIndex, hwStorageFCPortID, hwStorageFCPortStatus, hwStorageFCPortConfigRate, hwStorageFCPortMode, 
				hwStorageFCPortWWN, hwStorageISCSIPortIfIndex, hwStorageISCSIPortBoardIfIndex, hwStorageISCSIPortID, hwStorageISCSIPortStatus, 
				hwStorageISCSIPortIP, hwStorageISCSIPortNetMask, hwStorageISCSIPortBindMode, hwStorageLunID, hwStorageLunName, 
				hwStorageLunWWN, hwStorageLunOwningRaid, hwStorageLunCapacity, hwStorageLunOwningController, hwStorageLunStripDepth, 
				hwStorageLunWriteStrategy, hwStorageLunPrefetchValue, hwStorageLunStatus, hwStorageLunRowStatus, hwStorageReplicationPipenID, 
				hwStorageReplicationPipeType, hwStorageReplicationPipeStatus, hwStorageReplicationPipeUsed, hwStorageReplicationPipeMirrorLink, hwStorageReplicationPipeMirrorLinkTimeout, 
				hwStorageReplicationPipeRemoteArrayID, hwStorageReplicationPipeRemoteArrayWWN, hwStorageReplicationPipeLocalController, hwStorageReplicationPipeRemoteController, hwStorageReplicationPipeLocalPort, 
				hwStorageReplicationPipeRemotePort, hwStorageReplicationPipeLocalWWPN, hwStorageReplicationPipeRemoteWWPN, hwStorageReplicationPipeTargetName, hwStorageReplicationPipeInitiatorName, 
				hwStorageReplicationPipeRowStatus, version, totalCapacity, usedCapacity, deviceType, 
				deviceId, hwStorageEnclosureIfIndex, hwStorageControllerBoardEnclosureIfIndex, hwStorageInterfaceBoardEnclosureIfIndex, hwStorageExpansionBoardEnclosureIfIndex, 
				hwStorageSASPortIfIndex, hwStorageSASPortBoardIfIndex, hwStorageSASPortID, hwStorageSASPortStatus, hwStorageSASPortConfigRate, 
				hwStorageFrontEndHostPortIfIndex, hwStorageFrontEndHostPortType, hwStorageFrontEndHostPortStatus, hwStorageFrontEndHostPortPhysAddress, hwStorageFrontEndHostPortDescription, 
				hwStorageCacheID, hwStorageCacheTotalCapacity, hwStorageCacheHighWaterLevel, hwStorageCacheLowWaterLevel, hwStorageCacheRowStatus, 
				hwStorageNodeIfIndex, hwStorageNodeIPAddress, hwStorageNodeStatus, hwStorageNodeIsMaster, hwStorageNodeRowStatus, 
				deviceStatus, hwStorageControllerID, hwStorageControllerName, hwStorageControllerLocation, hwStorageControllerRunningStatus, 
				hwStorageControllerSoftVer, hwStorageControllerTemperature, hwStorageControllerIsMaster, hwStorageControllerELabel, hwStorageControllerPCBVer, 
				hwStorageControllerBMCVer, hwStorageControllerLogicVer, hwStorageControllerBIOSVer, hwStorageControllerMemorySize, hwStorageControllerCPUInfo, 
				hwStorageControllerVoltage, deviceTypeName, totalDiskNumber, hwStorageSASPortWWN, hwStorageFCPortLogicType, 
				hwStorageFCPortSpeedRate, hwStorageSASPortLogicType, hwStorageSASPortSpeedRate, hwStorageISCSIPortLogicType, hwStorageReplicationLinkID, 
				hwStorageReplicationLinkArrayID, hwStorageReplicationLinkType, hwStorageReplicationLinkStatus, hwStorageReplicationLinkUsed, hwStorageReplicationLinkRowStatus, 
				hwStorageLunPrefetchStrategy, status, hwStorageControllerHealthStatus }
			STATUS current
			DESCRIPTION 
				"Enter the description of the created OBJECT-GROUP."
			::= { isoGroups 1 }

		
		isoCompliances OBJECT IDENTIFIER ::= { isoConformance 2 }

		
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- ISM-STORAGE-SVC-MIB.mib
--
