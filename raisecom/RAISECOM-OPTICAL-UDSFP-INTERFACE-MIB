-- =======================================================================
-- RAISECOM-OPTICAL-UDSFP-INTERFACE-MIB.my
--
-- Version info 
-- 
-- Copyright(c) 2003-2005 by RAISECOM TECH, Ltd. 
-- All rights reserved.
-- =======================================================================
  
   
RAISECOM-OPTICAL-UDSFP-INTERFACE-MIB DEFINITIONS ::= BEGIN

	  IMPORTS
        MODULE-IDENTITY, OBJECT-TYPE, NOTIFICATION-TYPE, Integer32
                FROM SNMPv2-SMI                                     
        TEXTUAL-CONVENTION, DisplayString, TruthValue, TimeStamp
                FROM SNMPv2-TC                                      
        ifIndex                                                     
                FROM IF-MIB                                         
        optUdSysMgmt                                               
                FROM RAISECOM-BASE-MIB                              
--        RcOptModuleType, RcOptIfModuleType
--                FROM RAISECOM-OPTICAL-MODULE-TYPE-MIB
        rcNotifsTrapLocation
                FROM RAISECOM-NOTIFICATION-MIB
        rcEntPhysicalID
                FROM RAISECOM-OPTICAL-ENTITY-MIB;
                       
	raisecomOptUdSfpInterfaceMib   MODULE-IDENTITY
     
        LAST-UPDATED "2012062700Z"
        ORGANIZATION "OPCOM3500 Software Working Group"
        CONTACT-INFO
           "           "
        DESCRIPTION
              "The MIB module to describe Sfp interface objects."
		REVISION      "0711290000Z"
		DESCRIPTION
		"
		初始版本，由RAISECOM-OPTICAL-SFP-INTERFACE-MIB.my修改得来
		增加rcEntPhysicalID作为索引
		"
		REVISION	"0808110000Z"
        DESCRIPTION
			"
			1、增加了数字诊断DDM表；
			2、rcOptUdSfpOpticalInterface节点增加了枚举值
			"
		REVISION	"1003030000Z"
        DESCRIPTION
			"
			1、增加了当前15分钟数字诊断CurrentDDM表；
			2、增加了96个15分钟数字诊断IntervalDDM表；  
			3、增加数字诊断告警10对；   
			4、修改编译错误；
			by wuyanxiong
			"
		REVISION	"1005070000Z"
        DESCRIPTION
			"
			1、增加了rcOptUdSfpMediaType的fiber50uOM3(6)枚举值,from sfpif；
			--by huxuehai
			"	
		REVISION	"2011081100Z"
        DESCRIPTION
			"
			1、	修改rcOptUdSfpPortStatus bit表示范围为(1..4095)，支持激光器背光功率告警 
                和激光器寿命告警，与sfp同步；
			by yanghui
			"		
        
        REVISION	"2012062700Z"
        DESCRIPTION
			"
			1、新增一个节点rcOptUdSfpAlsDisable，用来实现ALS功能
			by yangchengming
			"
			        
        ::= { optUdSysMgmt 21 }  



--对象定义
    rcOptUdSfpInterfaceObjects       OBJECT IDENTIFIER ::= { raisecomOptUdSfpInterfaceMib 1 }
    rcOptUdSfpNotifications       OBJECT IDENTIFIER ::= { raisecomOptUdSfpInterfaceMib 2 }    

 
-- Sfp interface table

    rcOptUdSfpInterfaceTable OBJECT-TYPE
        SYNTAX SEQUENCE OF RcOptUdSfpInterfaceEntry
        MAX-ACCESS not-accessible
        STATUS current
        DESCRIPTION
        "
            Sfp接口的信息.
        " 
       ::= { rcOptUdSfpInterfaceObjects 1 }		
	
	rcOptUdSfpInterfaceEntry OBJECT-TYPE
        SYNTAX  RcOptUdSfpInterfaceEntry
        MAX-ACCESS not-accessible
        STATUS current
        DESCRIPTION
        " 
        "
        INDEX {rcEntPhysicalID, ifIndex }
        ::= { rcOptUdSfpInterfaceTable 1 }
        			
	RcOptUdSfpInterfaceEntry ::= SEQUENCE {
            rcOptUdSfpInterfaceId
                INTEGER,
            rcOptUdSfpExist
                INTEGER,
            rcOptUdSfpMediaType
                INTEGER,		 
    		rcOptUdSfpRXLOS
				INTEGER,
    		rcOptUdSfpTXFault
				INTEGER,     
    		rcOptUdSfpTXDisable
				INTEGER,                
            rcOptUdSfpModuleType    
                INTEGER, 
            rcOptUdSfpOpticalInterface	
            	INTEGER,     
            rcOptUdSfpSpeedStatus 
            	INTEGER,  
            rcOptUdSfpTransportDistance	
            	INTEGER, 
            rcOptUdSfpWaveLength
            	Integer32,
            rcOptUdSfpManufactory	
            	OCTET STRING,
            rcOptUdSfpProductType	
            	OCTET STRING,
            rcOptUdSfpVersion	
				OCTET STRING,
		    rcOptUdSfpWaterMask
				OCTET STRING,   
			rcOptUdSfpAlsDisable
				INTEGER
	}
	
	rcOptUdSfpInterfaceId OBJECT-TYPE
        SYNTAX  INTEGER 
        MAX-ACCESS read-only
        STATUS    current
        DESCRIPTION 
        "
            端口ID, 第一个端口Id为1,依次类推
        "  
        ::={ rcOptUdSfpInterfaceEntry 1 } 

	
		rcOptUdSfpExist OBJECT-TYPE
			SYNTAX INTEGER
			{
				exist(1), 
				notExist(2) 
			}
			MAX-ACCESS  read-only
			STATUS  current
			DESCRIPTION
			"
				模块在位通知
			"
		::= { rcOptUdSfpInterfaceEntry 3 }
	
		
		rcOptUdSfpMediaType OBJECT-TYPE
        SYNTAX  INTEGER   
        {
        	unknown(1),
        	fiber9u125u(2),
        	fiber50u125u(3),
        	fiber625u125u(4),
        	copper(5),
        	fiber50uOM3(6)      	
        }     
        MAX-ACCESS read-only
        STATUS    current
        DESCRIPTION 
        "
            介质类型
        "  
        ::={ rcOptUdSfpInterfaceEntry 4 } 	
	
		
		rcOptUdSfpRXLOS OBJECT-TYPE
			SYNTAX INTEGER
			{
				normal(1),
				alarm(2)
			}
			MAX-ACCESS  read-only
			STATUS  current
			DESCRIPTION
			"	
				光模块LOS状态
			"
			::= { rcOptUdSfpInterfaceEntry 5 }
	
		rcOptUdSfpTXFault OBJECT-TYPE
			SYNTAX INTEGER
			{
				normal(1), 
				alarm(2)
			}
			MAX-ACCESS  read-only
			STATUS  current
			DESCRIPTION
			"
				激光器发送故障
			"
			::= { rcOptUdSfpInterfaceEntry 6 }
	
		rcOptUdSfpTXDisable OBJECT-TYPE
			SYNTAX INTEGER
			{
				enable(1), 
				disable(2)
			}
			MAX-ACCESS  read-write
			STATUS  current
			DESCRIPTION
			"
				光信号发送禁止.即关闭光口
			"
			::= { rcOptUdSfpInterfaceEntry 7 }
	
	
		
		
	rcOptUdSfpModuleType OBJECT-TYPE
		SYNTAX INTEGER
		{ 
			unknown(1),
			gbic(2), 
			sff(3), 
			sfp(4)
		}
		MAX-ACCESS  read-only
		STATUS  current
		DESCRIPTION
		"
			模块类型
		"
		::= { rcOptUdSfpInterfaceEntry 9 }

	
	rcOptUdSfpOpticalInterface OBJECT-TYPE
		SYNTAX INTEGER
		{
			unknown(1),
			sc(2), 
			lc(3),
			rj45(4),
			fiber-channel-style1-copper-connector(5),
			fiber-channel-style2-copper-connector(6), 
			bnc-tnc(7),
			fiber-channel-coaxial-headers(8),
			fiber-jack(9),
			mt-rj(10), 
			mu(11),
			sg(12),
			optical-pigtail(13),
			hssdc-ii(22), 
			copper-pigtail(23)						
		}
		MAX-ACCESS  read-only
		STATUS  current
		DESCRIPTION
		"
			光连接头形式
		"
		::= { rcOptUdSfpInterfaceEntry 10 }
	
	rcOptUdSfpSpeedStatus OBJECT-TYPE
		SYNTAX INTEGER
		{ 
			unknown(1), 
			speed125M(2),
			speed155M(3),
			speed1250M(4),
			speed2500M(5),
 			speed622M(6)

		}
		MAX-ACCESS  read-only
		STATUS  current
		DESCRIPTION
		"
			 额定速率
		"
		::= { rcOptUdSfpInterfaceEntry 11 }
		
	rcOptUdSfpTransportDistance OBJECT-TYPE
		SYNTAX INTEGER
		MAX-ACCESS  read-only
		STATUS  current
		DESCRIPTION
		"
			传输距离.单位根据传输介质判断,对应关系如下 ：
			fiber9u125u(2)--单位 Km
			fiber50u125u(3)--单位 10m
			fiber625u125u(4)--单位 10m
			copper(5)--单位 m

		"
		::= { rcOptUdSfpInterfaceEntry 12 }	
	
	rcOptUdSfpWaveLength OBJECT-TYPE
		SYNTAX Integer32
		MAX-ACCESS  read-only
		STATUS  current
		DESCRIPTION
		"
			波长.单位nm
		"
		::= { rcOptUdSfpInterfaceEntry 13 }

	
	rcOptUdSfpManufactory OBJECT-TYPE
		SYNTAX OCTET STRING(SIZE (0..16))
		MAX-ACCESS  read-only
		STATUS  current
		DESCRIPTION
		"
			模块制造厂商
		"
		::= { rcOptUdSfpInterfaceEntry 14 }
	
	rcOptUdSfpProductType OBJECT-TYPE
		SYNTAX OCTET STRING(SIZE (0..16))
		MAX-ACCESS  read-only
		STATUS  current
		DESCRIPTION
		"
			产品型号
		"
		::= { rcOptUdSfpInterfaceEntry 15 }
	
	rcOptUdSfpVersion OBJECT-TYPE
		SYNTAX OCTET STRING(SIZE (0..4))
		MAX-ACCESS  read-only
		STATUS  current
		DESCRIPTION
		"
			模块版本号
		"
		::= { rcOptUdSfpInterfaceEntry 16 }
	
	rcOptUdSfpWaterMask OBJECT-TYPE
		SYNTAX OCTET STRING(SIZE (0..16))
		MAX-ACCESS  read-only
		STATUS  current
		DESCRIPTION
		"
			模块流水号
		"
		::= { rcOptUdSfpInterfaceEntry 17 }
	
	rcOptUdSfpAlsDisable OBJECT-TYPE
			SYNTAX INTEGER
			{
				enable(1), 
				disable(2)
			}
			MAX-ACCESS  read-write
			STATUS  current
			DESCRIPTION
			"
				激光器自动关断
			"
			::= { rcOptUdSfpInterfaceEntry 18 }
	
	-- Sfp interface DDM table

  rcOptUdSfpDDMTable OBJECT-TYPE
        SYNTAX SEQUENCE OF RcOptUdSfpDDMEntry
        MAX-ACCESS not-accessible
        STATUS current
        DESCRIPTION
        "
            Sfp接口的信息.
        " 
        ::= { rcOptUdSfpInterfaceObjects 2 }		
	
	rcOptUdSfpDDMEntry OBJECT-TYPE
        SYNTAX  RcOptUdSfpDDMEntry
        MAX-ACCESS not-accessible
        STATUS current
        DESCRIPTION
        " 
        "
        INDEX { rcEntPhysicalID, ifIndex }
        ::= { rcOptUdSfpDDMTable 1 }
        			
	RcOptUdSfpDDMEntry ::= SEQUENCE {
	          rcOptUdSfpPortTemperature
	            OCTET STRING,
	          rcOptUdSfpSupportDDM
	            INTEGER,
	          rcOptUdSfpPortVoltage
            	OCTET STRING,
	          rcOptUdSfpPortBiasCurrent
	            OCTET STRING,
	          rcOptUdSfpPortTxPower
	            OCTET STRING,
	          rcOptUdSfpPortRxPower
	            OCTET STRING,
	          rcOptUdSfpPortStatus
	            Integer32,   
	          rcOptUdSfpPortWarning  
	            Integer32,
	          rcOptSfpPortRegulator
	          	INTEGER	          
	}

	rcOptUdSfpSupportDDM OBJECT-TYPE
				SYNTAX INTEGER
				{ 
					support(1), 
					notsupport(2)
				}
				MAX-ACCESS  read-only
				STATUS  current
				DESCRIPTION
				"
					光模块是否支持数字诊断
				"
				::= { rcOptUdSfpDDMEntry 1 }

	rcOptUdSfpPortTemperature OBJECT-TYPE
				SYNTAX OCTET STRING(SIZE (0..16))
				MAX-ACCESS  read-only
				STATUS  current
				DESCRIPTION
				"
					光模块温度 -128℃ ~ +128℃
				"
				::= { rcOptUdSfpDDMEntry 2 }

	rcOptUdSfpPortVoltage OBJECT-TYPE
				SYNTAX OCTET STRING(SIZE (0..16))
				MAX-ACCESS  read-only
				STATUS  current
				DESCRIPTION
				"
					光模块电压 0 ~ 6.55V
				"
				::= { rcOptUdSfpDDMEntry 3 }
		
	rcOptUdSfpPortBiasCurrent OBJECT-TYPE
				SYNTAX OCTET STRING(SIZE (0..16))
				MAX-ACCESS  read-only
				STATUS  current
				DESCRIPTION
				"
					光模块偏置电流 0 ~ 131mA
				"
				::= { rcOptUdSfpDDMEntry 4 }
		
	rcOptUdSfpPortTxPower OBJECT-TYPE
				SYNTAX OCTET STRING(SIZE (0..16))
				MAX-ACCESS  read-only
				STATUS  current
				DESCRIPTION
				"
					光模块发送光功率 0 ~ 6.5535mW
				"
				::= { rcOptUdSfpDDMEntry 5 }
		
	rcOptUdSfpPortRxPower OBJECT-TYPE
				SYNTAX OCTET STRING(SIZE (0..16))
				MAX-ACCESS  read-only
				STATUS  current
				DESCRIPTION
				"
					光模块接收光功率 0 ~ 6.5535mW
				"
				::= { rcOptUdSfpDDMEntry 6 }
		    
	rcOptUdSfpPortStatus OBJECT-TYPE
        SYNTAX  Integer32 (1..4095)
        MAX-ACCESS  read-only
        STATUS  current
        DESCRIPTION
        "
        		模块性能超限警告，即alarm状态，bitmap表示，每个bit对应告警状态如下：
        		1   rcOptUdSfpTemperatureHighThreshold
        		2   rcOptUdSfpTemperatureLowThreshold
        		4   rcOptUdSfpVoltageHighThreshold
        		8   rcOptUdSfpVoltageLowThreshold  
        		16  rcOptUdSfpBiasCurrentHighThreshold
        		32  rcOptUdSfpBiasCurrentLowThreshold
        		64  rcOptUdSfpTxPowerHighThreshold
        		128  rcOptUdSfpTxPowerLowThreshold   
        		256  rcOptUdSfpRxPowerHighThreshold  
        		512  rcOptUdSfpRxPowerLowThreshold  
        		1024  rcOptUdSfpLDBackLightAlarm -- 激光器背光功率告警 
        		2048  rcOptUdSfpLDLifeAlarm -- 激光器寿命告警 
        "
        ::= { rcOptUdSfpDDMEntry 7 }
		    
	rcOptUdSfpPortWarning OBJECT-TYPE
		SYNTAX  Integer32 (1..1023)
		MAX-ACCESS  read-only
		STATUS  current
		DESCRIPTION
		"
			模块性能超限告警，即warning状态，比alarm的告警级别低，
			bitmap表示，每个bit对应告警状态如下：
			1   rcOptUdSfpTemperatureHighThreshold
			2   rcOptUdSfpTemperatureLowThreshold
			4   rcOptUdSfpVoltageHighThreshold
			8   rcOptUdSfpVoltageLowThreshold  
			16  rcOptUdSfpBiasCurrentHighThreshold
			32  rcOptUdSfpBiasCurrentLowThreshold
			64  rcOptUdSfpTxPowerHighThreshold
			128  rcOptUdSfpTxPowerLowThreshold   
			256  rcOptUdSfpRxPowerHighThreshold  
			512  rcOptUdSfpRxPowerLowThreshold  
		"
		::= { rcOptUdSfpDDMEntry 8 }
		rcOptSfpPortRegulator OBJECT-TYPE
				SYNTAX INTEGER
				{
					internally(1),
					externally(0),
					unknown(2)
				}
				MAX-ACCESS read-only
				STATUS current
				DESCRIPTION
					"  "
				::= { rcOptUdSfpDDMEntry 9 }


--  告警信息定义    
   
    rcOptUdSfpNotificationPrefix     OBJECT IDENTIFIER ::= { rcOptUdSfpNotifications 0 }             	
	
	rcOptUdSfpNotExistTrap NOTIFICATION-TYPE
		OBJECTS { rcNotifsTrapLocation, rcEntPhysicalID, ifIndex }
		STATUS             current
		DESCRIPTION
		"
			Sfp不在位通知信号.
		"
		::= { rcOptUdSfpNotificationPrefix 102301 }
	
	rcOptUdSfpExistTrap NOTIFICATION-TYPE
		OBJECTS { rcNotifsTrapLocation, rcEntPhysicalID, ifIndex }
		STATUS             current
		DESCRIPTION
		"
			Sfp在位通知信号.
		"
		::= { rcOptUdSfpNotificationPrefix 102302 }
	
	rcOptUdSfpTXFaultTrap NOTIFICATION-TYPE
		OBJECTS { rcNotifsTrapLocation, rcEntPhysicalID, ifIndex }
		STATUS             current
		DESCRIPTION
		"
			激光器发送故障.
		"
		::= { rcOptUdSfpNotificationPrefix 102303 }
	
	rcOptUdSfpTXFaultTrapOK NOTIFICATION-TYPE
		OBJECTS { rcNotifsTrapLocation, rcEntPhysicalID, ifIndex }
		STATUS             current
		DESCRIPTION
		"
			激光器发送故障清除.
		"
		::= { rcOptUdSfpNotificationPrefix 102304 }
	
	rcOptUdSfpRXLOSTrap NOTIFICATION-TYPE
		OBJECTS { rcNotifsTrapLocation, rcEntPhysicalID, ifIndex }
		STATUS             current
		DESCRIPTION
		"
			接收LOS告警.
		"
		::= { rcOptUdSfpNotificationPrefix 102305 }
	
	rcOptUdSfpRXLOSTrapOK NOTIFICATION-TYPE
		OBJECTS { rcNotifsTrapLocation, rcEntPhysicalID, ifIndex }
		STATUS             current
		DESCRIPTION
		"
			Sfp接收LOS清除.
		"
		::= { rcOptUdSfpNotificationPrefix 102306 }

	rcOptUdSfpTempHighTrap NOTIFICATION-TYPE
		OBJECTS { rcNotifsTrapLocation, rcEntPhysicalID, ifIndex }
		STATUS             current
		DESCRIPTION
		"
			温度超过上限alarm.
		"
		::= { rcOptUdSfpNotificationPrefix 102307 }

	rcOptUdSfpTempHighTrapOK NOTIFICATION-TYPE
		OBJECTS { rcNotifsTrapLocation, rcEntPhysicalID, ifIndex }
		STATUS             current
		DESCRIPTION
		"
			温度超过上限alarm恢复.
		"
		::= { rcOptUdSfpNotificationPrefix 102308 }

	rcOptUdSfpTempLowTrap NOTIFICATION-TYPE
		OBJECTS { rcNotifsTrapLocation, rcEntPhysicalID, ifIndex }
		STATUS             current
		DESCRIPTION
		"
			温度低于下限alarm
		"
		::= { rcOptUdSfpNotificationPrefix 102309 }

	rcOptUdSfpTempLowTrapOK NOTIFICATION-TYPE
		OBJECTS { rcNotifsTrapLocation, rcEntPhysicalID, ifIndex }
		STATUS             current
		DESCRIPTION
		"
			温度低于下限alarm恢复.
		"
		::= { rcOptUdSfpNotificationPrefix 102310 }

	rcOptUdSfpVccHighTrap NOTIFICATION-TYPE
		OBJECTS { rcNotifsTrapLocation, rcEntPhysicalID, ifIndex }
		STATUS             current
		DESCRIPTION
		"
			电压超过上限alarm.
		"
		::= { rcOptUdSfpNotificationPrefix 102311 }

	rcOptUdSfpVccHighTrapOK NOTIFICATION-TYPE
		OBJECTS { rcNotifsTrapLocation, rcEntPhysicalID, ifIndex }
		STATUS             current
		DESCRIPTION
		"
			电压超过上限alarm恢复.
		"
		::= { rcOptUdSfpNotificationPrefix 102312 }


	rcOptUdSfpVccLowTrap NOTIFICATION-TYPE
		OBJECTS { rcNotifsTrapLocation, rcEntPhysicalID, ifIndex }
		STATUS             current
		DESCRIPTION
		"
			电压低于下限alarm.
		"
		::= { rcOptUdSfpNotificationPrefix 102313 }

	rcOptUdSfpVccLowTrapOK NOTIFICATION-TYPE
		OBJECTS { rcNotifsTrapLocation, rcEntPhysicalID, ifIndex }
		STATUS             current
		DESCRIPTION
		"
			电压低于下限alarm恢复.
		"
		::= { rcOptUdSfpNotificationPrefix 102314 }

	rcOptUdSfpTxBiasHighTrap NOTIFICATION-TYPE
		OBJECTS { rcNotifsTrapLocation, rcEntPhysicalID, ifIndex }
		STATUS             current
		DESCRIPTION
		"
			电流超过上限alarm.
		"
		::= { rcOptUdSfpNotificationPrefix 102315 }

	rcOptUdSfpTxBiasHighTrapOK NOTIFICATION-TYPE
		OBJECTS { rcNotifsTrapLocation, rcEntPhysicalID, ifIndex }
		STATUS             current
		DESCRIPTION
		"
			电流超过上限alarm恢复.
		"
		::= { rcOptUdSfpNotificationPrefix 102316 }

	rcOptUdSfpTxBiasLowTrap NOTIFICATION-TYPE
		OBJECTS { rcNotifsTrapLocation, rcEntPhysicalID, ifIndex }
		STATUS             current
		DESCRIPTION
		"
			电流低于下限alarm.
		"
		::= { rcOptUdSfpNotificationPrefix 102317 }

	rcOptUdSfpTxBiasLowTrapOK NOTIFICATION-TYPE
		OBJECTS { rcNotifsTrapLocation, rcEntPhysicalID, ifIndex }
		STATUS             current
		DESCRIPTION
		"
			电流低于下限alarm恢复.
		"
		::= { rcOptUdSfpNotificationPrefix 102318 }
		
	rcOptUdSfpTxPowerHighTrap NOTIFICATION-TYPE
		OBJECTS { rcNotifsTrapLocation, rcEntPhysicalID, ifIndex }
		STATUS             current
		DESCRIPTION
		"
			发光功率超过上限alarm.
		"
		::= { rcOptUdSfpNotificationPrefix 102319 }

	rcOptUdSfpTxPowerHighTrapOK NOTIFICATION-TYPE
		OBJECTS { rcNotifsTrapLocation, rcEntPhysicalID, ifIndex }
		STATUS             current
		DESCRIPTION
		"
			发光功率超过上限alarm恢复.
		"
		::= { rcOptUdSfpNotificationPrefix 102320 }

	rcOptUdSfpTxPowerLowTrap NOTIFICATION-TYPE
		OBJECTS { rcNotifsTrapLocation, rcEntPhysicalID, ifIndex }
		STATUS             current
		DESCRIPTION
		"
			发光功率低于下限alarm.
		"
		::= { rcOptUdSfpNotificationPrefix 102321 }

	rcOptUdSfpTxPowerLowTrapOK NOTIFICATION-TYPE
		OBJECTS { rcNotifsTrapLocation, rcEntPhysicalID, ifIndex }
		STATUS             current
		DESCRIPTION
		"
			发光功率低于下限alarm恢复.
		"
		::= { rcOptUdSfpNotificationPrefix 102322 }

	rcOptUdSfpRxPowerHighTrap NOTIFICATION-TYPE
		OBJECTS { rcNotifsTrapLocation, rcEntPhysicalID, ifIndex }
		STATUS             current
		DESCRIPTION
		"
			收光功率超过上限alarm.
		"
		::= { rcOptUdSfpNotificationPrefix 102323 }

	rcOptUdSfpRxPowerHighTrapOK NOTIFICATION-TYPE
		OBJECTS { rcNotifsTrapLocation, rcEntPhysicalID, ifIndex }
		STATUS             current
		DESCRIPTION
		"
			收光功率超过上限alarm恢复.
		"
		::= { rcOptUdSfpNotificationPrefix 102324 }

	rcOptUdSfpRxPowerLowTrap NOTIFICATION-TYPE
		OBJECTS { rcNotifsTrapLocation, rcEntPhysicalID, ifIndex }
		STATUS             current
		DESCRIPTION
		"
			收光功率低于下限alarm.
		"
		::= { rcOptUdSfpNotificationPrefix 102325 }

	rcOptUdSfpRxPowerLowTrapOK NOTIFICATION-TYPE
		OBJECTS { rcNotifsTrapLocation, rcEntPhysicalID, ifIndex }
		STATUS             current
		DESCRIPTION
		"
			收光功率低于下限alarm恢复.
		"
		::= { rcOptUdSfpNotificationPrefix 102326 }


	-- Sfp interface Current DDM table

  rcOptUdSfpCurrentDDMTable OBJECT-TYPE
        SYNTAX SEQUENCE OF rcOptUdSfpCurrentDDMEntry
        MAX-ACCESS not-accessible
        STATUS current
        DESCRIPTION
        "
            Sfp当前15分钟数字诊断信息.
        " 
        ::= { rcOptUdSfpInterfaceObjects 3 }		
	
	rcOptUdSfpCurrentDDMEntry OBJECT-TYPE
        SYNTAX  rcOptUdSfpCurrentDDMEntry
        MAX-ACCESS not-accessible
        STATUS current
        DESCRIPTION
        " 
        "
        INDEX { rcEntPhysicalID, ifIndex }
        ::= { rcOptUdSfpCurrentDDMTable 1 }
        			
	rcOptUdSfpCurrentDDMEntry ::= SEQUENCE {
	          rcOptUdSfpPortCurrentTemperature
	            OCTET STRING,
	          rcOptUdSfpPortCurrentVoltage
            	OCTET STRING,
	          rcOptUdSfpPortCurrentBiasCurrent
	            OCTET STRING,
	          rcOptUdSfpPortCurrentTxPower
	            OCTET STRING,
	          rcOptUdSfpPortCurrentRxPower
	            OCTET STRING
        
	}

	rcOptUdSfpPortCurrentTemperature OBJECT-TYPE
				SYNTAX OCTET STRING(SIZE (0..16))
				MAX-ACCESS  read-only
				STATUS  current
				DESCRIPTION
				"
					当前15分钟内光模块温度 -128℃ ~ +128℃
				"
				::= { rcOptUdSfpCurrentDDMEntry 1 }

	rcOptUdSfpPortCurrentVoltage OBJECT-TYPE
				SYNTAX OCTET STRING(SIZE (0..16))
				MAX-ACCESS  read-only
				STATUS  current
				DESCRIPTION
				"
					当前15分钟内光模块电压 0 ~ 6.55V
				"
				::= { rcOptUdSfpCurrentDDMEntry 2 }
		
	rcOptUdSfpPortCurrentBiasCurrent OBJECT-TYPE
				SYNTAX OCTET STRING(SIZE (0..16))
				MAX-ACCESS  read-only
				STATUS  current
				DESCRIPTION
				"
					当前15分钟内光模块偏置电流 0 ~ 131mA
				"
				::= { rcOptUdSfpCurrentDDMEntry 3 }
		
	rcOptUdSfpPortCurrentTxPower OBJECT-TYPE
				SYNTAX OCTET STRING(SIZE (0..16))
				MAX-ACCESS  read-only
				STATUS  current
				DESCRIPTION
				"
					当前15分钟内光模块发送光功率 0 ~ 6.5535mW
				"
				::= { rcOptUdSfpCurrentDDMEntry 4 }
		
	rcOptUdSfpPortCurrentRxPower OBJECT-TYPE
				SYNTAX OCTET STRING(SIZE (0..16))
				MAX-ACCESS  read-only
				STATUS  current
				DESCRIPTION
				"
					当前15分钟内光模块接收光功率 0 ~ 6.5535mW
				"
				::= { rcOptUdSfpCurrentDDMEntry 5 }
		    
	-- Sfp interface 15min *96 DDM table

  rcOptUdSfpIntervalDDMTable OBJECT-TYPE
        SYNTAX SEQUENCE OF rcOptUdSfpIntervalDDMEntry
        MAX-ACCESS not-accessible
        STATUS current
        DESCRIPTION
        "
        	sfp diagnoinfo during the interval
        " 
        ::= { rcOptUdSfpInterfaceObjects 4 }		
	
	rcOptUdSfpIntervalDDMEntry OBJECT-TYPE
        SYNTAX  rcOptUdSfpIntervalDDMEntry
        MAX-ACCESS not-accessible
        STATUS current
        DESCRIPTION
        "  
        "
        INDEX { rcEntPhysicalID, ifIndex, rcOptUdSfpPortIntervalNumber}
        ::= { rcOptUdSfpIntervalDDMTable 1 }
        			
	rcOptUdSfpIntervalDDMEntry ::= SEQUENCE {
			  rcOptUdSfpPortIntervalNumber
			  	INTEGER,	
	          rcOptUdSfpPortIntervalTemperature
	            OCTET STRING,
	          rcOptUdSfpPortIntervalVoltage
            	OCTET STRING,
	          rcOptUdSfpPortIntervalBiasCurrent
	            OCTET STRING,
	          rcOptUdSfpPortIntervalTxPower
	            OCTET STRING,
	          rcOptUdSfpPortIntervalRxPower
	            OCTET STRING
        
	}
		 
	rcOptUdSfpPortIntervalNumber OBJECT-TYPE
		 		SYNTAX INTEGER
		 		MAX-ACCESS  read-only
		 		STATUS current
		 		DESCRIPTION
		 		"
		 			Ud sfp PORT 第几个十五分钟
		 		"  	                          
		 		::= { rcOptUdSfpIntervalDDMEntry 1 }

	rcOptUdSfpPortIntervalTemperature OBJECT-TYPE
				SYNTAX OCTET STRING(SIZE (0..16))
				MAX-ACCESS  read-only
				STATUS  current
				DESCRIPTION
				"
					this OBJECT indicates the average temperature in the interval 15 minute interval.
					 -128℃ ~ +128℃
				"
				::= { rcOptUdSfpIntervalDDMEntry 2 }

	rcOptUdSfpPortIntervalVoltage OBJECT-TYPE
				SYNTAX OCTET STRING(SIZE (0..16))
				MAX-ACCESS  read-only
				STATUS  current
				DESCRIPTION
				"
					This OBJECT indicates the averaget voltage in the interval 15 minute interval.
					 0 ~ 6.55V
				"
				::= { rcOptUdSfpIntervalDDMEntry 3 }
		
	rcOptUdSfpPortIntervalBiasCurrent OBJECT-TYPE
				SYNTAX OCTET STRING(SIZE (0..16))
				MAX-ACCESS  read-only
				STATUS  current
				DESCRIPTION
				"
					The object indicates the average offset interval in the interval
					 0 ~ 131mA
				"
				::= { rcOptUdSfpIntervalDDMEntry 4 }
		
	rcOptUdSfpPortIntervalTxPower OBJECT-TYPE
				SYNTAX OCTET STRING(SIZE (0..16))
				MAX-ACCESS  read-only
				STATUS  current
				DESCRIPTION
				"
					This object indicates the average receive power  in the interval
					0 ~ 6.5535mW
				"
				::= { rcOptUdSfpIntervalDDMEntry 5 }
		
	rcOptUdSfpPortIntervalRxPower OBJECT-TYPE
				SYNTAX OCTET STRING(SIZE (0..16))
				MAX-ACCESS  read-only
				STATUS  current
				DESCRIPTION
				"
					This object indicates the average send power in the interval
					0 ~ 6.5535mW
				"
				::= { rcOptUdSfpIntervalDDMEntry 6 }
  		  
END
