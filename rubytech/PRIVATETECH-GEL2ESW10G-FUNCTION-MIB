PRIVATETECH-GEL2ESW10G-FUNCTION-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

privatetech MODULE-IDENTITY
        LAST-UPDATED "201203290000Z"
        ORGANIZATION "Corp."
        CONTACT-INFO
            ""
        DESCRIPTION
            ""
        ::= { enterprises 5205 }

switch                                                          OBJECT IDENTIFIER ::= { privatetech 2 }

gel2esw10gProductId                                             OBJECT IDENTIFIER ::= { switch 51 }

gel2esw10gSystem                                                OBJECT IDENTIFIER ::= { gel2esw10gProductId 1 }

gel2esw10gSystemInformation                                     OBJECT IDENTIFIER ::= { gel2esw10gSystem 1 }

gel2esw10gModelName OBJECT-TYPE
   SYNTAX       DisplayString
   MAX-ACCESS   read-only
   STATUS       current
   DESCRIPTION
       ""
 ::= { gel2esw10gSystemInformation 1 }

gel2esw10gBIOSVersion OBJECT-TYPE
   SYNTAX       DisplayString
   MAX-ACCESS   read-only
   STATUS       current
   DESCRIPTION
       ""
   ::= { gel2esw10gSystemInformation 2 }

gel2esw10gFirmwareVersion OBJECT-TYPE
   SYNTAX       DisplayString
   MAX-ACCESS   read-only
   STATUS       current
   DESCRIPTION
       ""
   ::= { gel2esw10gSystemInformation 3 }

gel2esw10gHardwareMechanicalVersion OBJECT-TYPE
   SYNTAX       DisplayString
   MAX-ACCESS   read-only
   STATUS       current
   DESCRIPTION
       ""
   ::= { gel2esw10gSystemInformation 4 }

gel2esw10gSeriesNumber OBJECT-TYPE
   SYNTAX       DisplayString
   MAX-ACCESS   read-only
   STATUS       current
   DESCRIPTION
       ""
   ::= { gel2esw10gSystemInformation 5 }

gel2esw10gHostMACAddress OBJECT-TYPE
   SYNTAX       MacAddress
   MAX-ACCESS   read-only
   STATUS       current
   DESCRIPTION
       ""
   ::= { gel2esw10gSystemInformation 6 }

gel2esw10gConsoleBaudrate OBJECT-TYPE
   SYNTAX       DisplayString
   MAX-ACCESS   read-only
   STATUS       current
   DESCRIPTION
       ""
   ::= { gel2esw10gSystemInformation 7 }

gel2esw10gRAMSize OBJECT-TYPE
   SYNTAX       DisplayString
   MAX-ACCESS   read-only
   STATUS       current
   DESCRIPTION
       ""
   ::= { gel2esw10gSystemInformation 8 }

gel2esw10gFlashSize OBJECT-TYPE
   SYNTAX       DisplayString
   MAX-ACCESS   read-only
   STATUS       current
   DESCRIPTION
       ""
   ::= { gel2esw10gSystemInformation 9 }

gel2esw10gBridgeFBDSize OBJECT-TYPE
   SYNTAX       DisplayString
   MAX-ACCESS   read-only
   STATUS       current
   DESCRIPTION
       ""
   ::= { gel2esw10gSystemInformation 10 }

gel2esw10gTransmitQueue OBJECT-TYPE
   SYNTAX       DisplayString
   MAX-ACCESS   read-only
   STATUS       current
   DESCRIPTION
       ""
   ::= { gel2esw10gSystemInformation 11 }

gel2esw10gMaximumFrameSize OBJECT-TYPE
   SYNTAX       DisplayString
   MAX-ACCESS   read-only
   STATUS       current
   DESCRIPTION
       ""
   ::= { gel2esw10gSystemInformation 12 }

gel2esw10gCPULoad OBJECT-TYPE
   SYNTAX       DisplayString
   MAX-ACCESS   read-only
   STATUS       current
   DESCRIPTION
       ""
   ::= { gel2esw10gSystemInformation 13 }


gel2esw10gSystemTime                                            OBJECT IDENTIFIER ::= { gel2esw10gSystem 2 }

gel2esw10gSystemTimeManual                                      OBJECT IDENTIFIER ::= { gel2esw10gSystemTime 1 }

gel2esw10gSystemTimeManualClockSource OBJECT-TYPE
   SYNTAX       INTEGER(0|1)
   MAX-ACCESS   read-write
   STATUS       current
   DESCRIPTION
       "default: 0,
        0 : Use Local Settings,
        1 : Use NTP Server."
   ::= { gel2esw10gSystemTimeManual 1 }
   
gel2esw10gSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gel2esw10gSystemTimeManual 2 }

gel2esw10gSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gel2esw10gSystemTimeManual 3 }
   
gel2esw10gSystemTimeManualDaylightSavings OBJECT-TYPE
   SYNTAX       INTEGER(0|1)
   MAX-ACCESS   read-write
   STATUS       current
   DESCRIPTION
       "default: 0,
        0 : Disable,
        1 : Enable."
   ::= { gel2esw10gSystemTimeManual 4 }
   
gel2esw10gSystemTimeManualTimeSetOffset OBJECT-TYPE
   SYNTAX       INTEGER(1..1440)
   MAX-ACCESS   read-write
   STATUS       current
   DESCRIPTION
       "Get/Set the Daylight Saving Time.
        The value range is between 1 and 1440 (minutes),
        Default : 60 (minutes)."
   ::= { gel2esw10gSystemTimeManual 5 }
   
gel2esw10gSystemTimeManualDaylightSavingsType OBJECT-TYPE
   SYNTAX       INTEGER(0|1)
   MAX-ACCESS   read-write
   STATUS       current
   DESCRIPTION
       "default: 0,
        0 : By dates,
        1 : Recurring."
   ::= { gel2esw10gSystemTimeManual 6 }
   
gel2esw10gSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gel2esw10gSystemTimeManual 7 }
   
gel2esw10gSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gel2esw10gSystemTimeManual 8 }

gel2esw10gSystemTimeManualDaylightSavingsRecurringDayFrom OBJECT-TYPE
   SYNTAX       INTEGER(0..6)
   MAX-ACCESS   read-write
   STATUS       current
   DESCRIPTION
       "Get/Set the Daylight Saving Time Day From.
        0 : Sun, 1 : Mon, 2 : Tue, 3 : Wed, 4 : Thu, 5 : Fri, 6 : Sat."
   ::= { gel2esw10gSystemTimeManual 9 }

gel2esw10gSystemTimeManualDaylightSavingsRecurringWeekFrom OBJECT-TYPE
   SYNTAX       INTEGER(1..5)
   MAX-ACCESS   read-write
   STATUS       current
   DESCRIPTION
       "Get/Set the Daylight Saving Time Week From.
        1 : first week, 2, 3, 4, 5 : last week"
   ::= { gel2esw10gSystemTimeManual 10 }
   
gel2esw10gSystemTimeManualDaylightSavingsRecurringMonthFrom OBJECT-TYPE
   SYNTAX       INTEGER(0..11)
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gel2esw10gSystemTimeManual 11 }

gel2esw10gSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gel2esw10gSystemTimeManual 12 }
   
gel2esw10gSystemTimeManualDaylightSavingsRecurringDayTo OBJECT-TYPE
   SYNTAX       INTEGER(0..6)
   MAX-ACCESS   read-write
   STATUS       current
   DESCRIPTION
       "Get/Set the Daylight Saving Time Day To.
        0 : Sun, 1 : Mon, 2 : Tue, 3 : Wed, 4 : Thu, 5 : Fri, 6 : Sat."
   ::= { gel2esw10gSystemTimeManual 13 }

gel2esw10gSystemTimeManualDaylightSavingsRecurringWeekTo OBJECT-TYPE
   SYNTAX       INTEGER(1..5)
   MAX-ACCESS   read-write
   STATUS       current
   DESCRIPTION
       "Get/Set the Daylight Saving Time Week To.
        1 : first week, 2, 3, 4, 5 : last week"
   ::= { gel2esw10gSystemTimeManual 14 }
   
gel2esw10gSystemTimeManualDaylightSavingsRecurringMonthTo OBJECT-TYPE
   SYNTAX       INTEGER(0..11)
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gel2esw10gSystemTimeManual 15 }

gel2esw10gSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gel2esw10gSystemTimeManual 16 }

gel2esw10gSystemTimeNTP                                     OBJECT IDENTIFIER ::= { gel2esw10gSystemTime 2 }

gel2esw10gSystemTimeNTPTable OBJECT-TYPE
   SYNTAX      SEQUENCE OF GEL2ESW10GSystemTimeNTPEntry
   MAX-ACCESS  not-accessible
   STATUS      current
   DESCRIPTION
       " "
   ::= { gel2esw10gSystemTimeNTP 1 }

gel2esw10gSystemTimeNTPEntry OBJECT-TYPE
   SYNTAX      GEL2ESW10GSystemTimeNTPEntry
   MAX-ACCESS  not-accessible
   STATUS      current
   DESCRIPTION
       ""
   INDEX    { gel2esw10gSystemTimeNTPIndex  }
   ::= { gel2esw10gSystemTimeNTPTable 1 }

GEL2ESW10GSystemTimeNTPEntry ::= SEQUENCE {
   gel2esw10gSystemTimeNTPIndex             INTEGER,
   gel2esw10gSystemTimeNTPServerIPType      INTEGER,
   gel2esw10gSystemTimeNTPServer            DisplayString,
   gel2esw10gSystemTimeNTPCurrentMode       INTEGER
}

gel2esw10gSystemTimeNTPIndex OBJECT-TYPE
   SYNTAX      INTEGER (1..5)
   MAX-ACCESS  not-accessible
   STATUS      current
   DESCRIPTION
       " The index of the ntp entry. "
   ::= { gel2esw10gSystemTimeNTPEntry 1 }

gel2esw10gSystemTimeNTPServerIPType OBJECT-TYPE
   SYNTAX       INTEGER(0|1)
   MAX-ACCESS   read-write
   STATUS       current
   DESCRIPTION
       "Default: 0,
        0 : IPv4,
        1 : IPv6."
   ::= { gel2esw10gSystemTimeNTPEntry 2 }

gel2esw10gSystemTimeNTPServer OBJECT-TYPE
   SYNTAX       DisplayString
   MAX-ACCESS   read-write
   STATUS       current
   DESCRIPTION
       "Get/Set the NTP Time Server1. You can use the IP address or domain name."
   ::= { gel2esw10gSystemTimeNTPEntry 3 }

gel2esw10gSystemTimeNTPCurrentMode OBJECT-TYPE
   SYNTAX      INTEGER (0..3)
   MAX-ACCESS  read-write
   STATUS      current
   DESCRIPTION
       " 0: Empty
        1: Active
        2: Edit
        3: Delete"
   ::= { gel2esw10gSystemTimeNTPEntry 4 }
    

gel2esw10gSystemAccount                                         OBJECT IDENTIFIER ::= { gel2esw10gSystem 3 }

gel2esw10gSystemAccountUsers                                    OBJECT IDENTIFIER ::= { gel2esw10gSystemAccount 1 }

gel2esw10gSystemAccountUserCreate OBJECT-TYPE
   SYNTAX       INTEGER(0|1)
   MAX-ACCESS   read-write
   STATUS       current
   DESCRIPTION
       "default: 0
        0 : None  (read only)
        1 : Create a user account"
   ::= { gel2esw10gSystemAccountUsers 1 }

gel2esw10gSystemAccountUsersTable OBJECT-TYPE
   SYNTAX      SEQUENCE OF GEL2ESW10GSystemAccountUsersEntry
   MAX-ACCESS  not-accessible
   STATUS      current
   DESCRIPTION
       " "
   ::= { gel2esw10gSystemAccountUsers 2 }

gel2esw10gSystemAccountUsersEntry OBJECT-TYPE
   SYNTAX      GEL2ESW10GSystemAccountUsersEntry
   MAX-ACCESS  not-accessible
   STATUS      current
   DESCRIPTION
       ""
   INDEX    { gel2esw10gUserIndex  }
   ::= { gel2esw10gSystemAccountUsersTable 1 }


GEL2ESW10GSystemAccountUsersEntry ::= SEQUENCE {
   gel2esw10gUserIndex              INTEGER,
   gel2esw10gUserName               DisplayString,
   gel2esw10gPassword               DisplayString,
   gel2esw10gUserPrivilegeLevel     INTEGER,
   gel2esw10gAccountUserRowStatus   INTEGER
}


gel2esw10gUserIndex OBJECT-TYPE
   SYNTAX      INTEGER (1..20)
   MAX-ACCESS  not-accessible
   STATUS      current
   DESCRIPTION
       " "
   ::= { gel2esw10gSystemAccountUsersEntry 1 }

gel2esw10gUserName OBJECT-TYPE
   SYNTAX      DisplayString (SIZE (1..32))
   MAX-ACCESS  read-write
   STATUS      current
   DESCRIPTION
       " "
   ::= { gel2esw10gSystemAccountUsersEntry 2 }

gel2esw10gPassword OBJECT-TYPE
   SYNTAX      DisplayString (SIZE (1..32))
   MAX-ACCESS  read-write
   STATUS      current
   DESCRIPTION
       " "
   ::= { gel2esw10gSystemAccountUsersEntry 3 }

gel2esw10gUserPrivilegeLevel OBJECT-TYPE
   SYNTAX      INTEGER (1..15)
   MAX-ACCESS  read-write
   STATUS      current
   DESCRIPTION
       "default:1 
        User privilege level range : 1 - 15"
   ::= { gel2esw10gSystemAccountUsersEntry 4 }

gel2esw10gAccountUserRowStatus OBJECT-TYPE
   SYNTAX      INTEGER (1..5)
   MAX-ACCESS  read-write
   STATUS      current
   DESCRIPTION
       " 1: active
        2: notInservice
        3: edit
        4: destroy
        5: undo"
   ::= { gel2esw10gSystemAccountUsersEntry 5 }

gel2esw10gSystemAccountPrivilegeLevel                           OBJECT IDENTIFIER ::= { gel2esw10gSystemAccount 2 }

gel2esw10gAccountPrivilegeLevel OBJECT-TYPE
   SYNTAX      INTEGER (1..15)
   MAX-ACCESS  read-write
   STATUS      current
   DESCRIPTION
       "default:10 "
   ::= { gel2esw10gSystemAccountPrivilegeLevel 1 }

gel2esw10gAggregationPrivilegeLevel OBJECT-TYPE
   SYNTAX      INTEGER (1..15)
   MAX-ACCESS  read-write
   STATUS      current
   DESCRIPTION
       "default:10 "
   ::= { gel2esw10gSystemAccountPrivilegeLevel 2 }

gel2esw10gDiagnosticsPrivilegeLevel OBJECT-TYPE
   SYNTAX      INTEGER (1..15)
   MAX-ACCESS  read-write
   STATUS      current
   DESCRIPTION
       "default:10 "
   ::= { gel2esw10gSystemAccountPrivilegeLevel 3 }

gel2esw10gEEEPrivilegeLevel OBJECT-TYPE
   SYNTAX      INTEGER (1..15)
   MAX-ACCESS  read-write
   STATUS      current
   DESCRIPTION
       "default:10 "
   ::= { gel2esw10gSystemAccountPrivilegeLevel 4 }

gel2esw10gEasyportPrivilegeLevel OBJECT-TYPE
   SYNTAX      INTEGER (1..15)
   MAX-ACCESS  read-write
   STATUS      current
   DESCRIPTION
       "default:10 "
   ::= { gel2esw10gSystemAccountPrivilegeLevel 5 }

gel2esw10gGARPPrivilegeLevel OBJECT-TYPE
   SYNTAX      INTEGER (1..15)
   MAX-ACCESS  read-write
   STATUS      current
   DESCRIPTION
       "default:10 "
   ::= { gel2esw10gSystemAccountPrivilegeLevel 6 }

gel2esw10gGVRPPrivilegeLevel OBJECT-TYPE
   SYNTAX      INTEGER (1..15)
   MAX-ACCESS  read-write
   STATUS      current
   DESCRIPTION
       "default:10 "
   ::= { gel2esw10gSystemAccountPrivilegeLevel 7 }

gel2esw10gIPPrivilegeLevel OBJECT-TYPE
   SYNTAX      INTEGER (1..15)
   MAX-ACCESS  read-write
   STATUS      current
   DESCRIPTION
       "default:10 "
   ::= { gel2esw10gSystemAccountPrivilegeLevel 8 }

gel2esw10gIPMCSnoopingPrivilegeLevel OBJECT-TYPE
   SYNTAX      INTEGER (1..15)
   MAX-ACCESS  read-write
   STATUS      current
   DESCRIPTION
       "default:10 "
   ::= { gel2esw10gSystemAccountPrivilegeLevel 9 }

gel2esw10gLACPPrivilegeLevel OBJECT-TYPE
   SYNTAX      INTEGER (1..15)
   MAX-ACCESS  read-write
   STATUS      current
   DESCRIPTION
       "default:10 "
   ::= { gel2esw10gSystemAccountPrivilegeLevel 10 }

gel2esw10gLLDPPrivilegeLevel OBJECT-TYPE
   SYNTAX      INTEGER (1..15)
   MAX-ACCESS  read-write
   STATUS      current
   DESCRIPTION
       "default:10 "
   ::= { gel2esw10gSystemAccountPrivilegeLevel 11 }

gel2esw10gLLDPMEDPrivilegeLevel OBJECT-TYPE
   SYNTAX      INTEGER (1..15)
   MAX-ACCESS  read-write
   STATUS      current
   DESCRIPTION
       "default:10 "
   ::= { gel2esw10gSystemAccountPrivilegeLevel 12 }

gel2esw10gMACTablePrivilegeLevel OBJECT-TYPE
   SYNTAX      INTEGER (1..15)
   MAX-ACCESS  read-write
   STATUS      current
   DESCRIPTION
       "default:10 "
   ::= { gel2esw10gSystemAccountPrivilegeLevel 13 }

gel2esw10gMRPPrivilegeLevel OBJECT-TYPE
   SYNTAX      INTEGER (1..15)
   MAX-ACCESS  read-write
   STATUS      current
   DESCRIPTION
       "default:10 "
   ::= { gel2esw10gSystemAccountPrivilegeLevel 14 }

gel2esw10gMVRPrivilegeLevel OBJECT-TYPE
   SYNTAX      INTEGER (1..15)
   MAX-ACCESS  read-write
   STATUS      current
   DESCRIPTION
       "default:10 "
   ::= { gel2esw10gSystemAccountPrivilegeLevel 15 }

gel2esw10gMVRPPrivilegeLevel OBJECT-TYPE
   SYNTAX      INTEGER (1..15)
   MAX-ACCESS  read-write
   STATUS      current
   DESCRIPTION
       "default:10 "
   ::= { gel2esw10gSystemAccountPrivilegeLevel 16 }

gel2esw10gMaintenancePrivilegeLevel OBJECT-TYPE
   SYNTAX      INTEGER (1..15)
   MAX-ACCESS  read-write
   STATUS      current
   DESCRIPTION
       "default:10 "
   ::= { gel2esw10gSystemAccountPrivilegeLevel 17 }

gel2esw10gMirroringPrivilegeLevel OBJECT-TYPE
   SYNTAX      INTEGER (1..15)
   MAX-ACCESS  read-write
   STATUS      current
   DESCRIPTION
       "default:10 "
   ::= { gel2esw10gSystemAccountPrivilegeLevel 18 }

gel2esw10gPortsPrivilegeLevel OBJECT-TYPE
   SYNTAX      INTEGER (1..15)
   MAX-ACCESS  read-write
   STATUS      current
   DESCRIPTION
       "default:10 "
   ::= { gel2esw10gSystemAccountPrivilegeLevel 19 }

gel2esw10gPrivateVLANsPrivilegeLevel OBJECT-TYPE
   SYNTAX      INTEGER (1..15)
   MAX-ACCESS  read-write
   STATUS      current
   DESCRIPTION
       "default:10 "
   ::= { gel2esw10gSystemAccountPrivilegeLevel 20 }

gel2esw10gQoSPrivilegeLevel OBJECT-TYPE
   SYNTAX      INTEGER (1..15)
   MAX-ACCESS  read-write
   STATUS      current
   DESCRIPTION
       "default:10 "
   ::= { gel2esw10gSystemAccountPrivilegeLevel 21 }

gel2esw10gSMTPPrivilegeLevel OBJECT-TYPE
   SYNTAX      INTEGER (1..15)
   MAX-ACCESS  read-write
   STATUS      current
   DESCRIPTION
       "default:10 "
   ::= { gel2esw10gSystemAccountPrivilegeLevel 22 }

gel2esw10gSNMPPrivilegeLevel OBJECT-TYPE
   SYNTAX      INTEGER (1..15)
   MAX-ACCESS  read-write
   STATUS      current
   DESCRIPTION
       "default:10 "
   ::= { gel2esw10gSystemAccountPrivilegeLevel 23 }

gel2esw10gSecurityPrivilegeLevel OBJECT-TYPE
   SYNTAX      INTEGER (1..15)
   MAX-ACCESS  read-write
   STATUS      current
   DESCRIPTION
       "default:10 "
   ::= { gel2esw10gSystemAccountPrivilegeLevel 24 }

gel2esw10gSpanningTreePrivilegeLevel OBJECT-TYPE
   SYNTAX      INTEGER (1..15)
   MAX-ACCESS  read-write
   STATUS      current
   DESCRIPTION
       "default:10 "
   ::= { gel2esw10gSystemAccountPrivilegeLevel 25 }

gel2esw10gSystemPrivilegeLevel OBJECT-TYPE
   SYNTAX      INTEGER (1..15)
   MAX-ACCESS  read-write
   STATUS      current
   DESCRIPTION
       "default:10 "
   ::= { gel2esw10gSystemAccountPrivilegeLevel 26 }

gel2esw10gTrapEventPrivilegeLevel OBJECT-TYPE
   SYNTAX      INTEGER (1..15)
   MAX-ACCESS  read-write
   STATUS      current
   DESCRIPTION
       "default:10 "
   ::= { gel2esw10gSystemAccountPrivilegeLevel 27 }

gel2esw10gVCLPrivilegeLevel OBJECT-TYPE
   SYNTAX      INTEGER (1..15)
   MAX-ACCESS  read-write
   STATUS      current
   DESCRIPTION
       "default:10 "
   ::= { gel2esw10gSystemAccountPrivilegeLevel 28 }

gel2esw10gVLANsPrivilegeLevel OBJECT-TYPE
   SYNTAX      INTEGER (1..15)
   MAX-ACCESS  read-write
   STATUS      current
   DESCRIPTION
       "default:10 "
   ::= { gel2esw10gSystemAccountPrivilegeLevel 29 }

gel2esw10gVoiceVLANPrivilegeLevel OBJECT-TYPE
   SYNTAX      INTEGER (1..15)
   MAX-ACCESS  read-write
   STATUS      current
   DESCRIPTION
       "default:10 "
   ::= { gel2esw10gSystemAccountPrivilegeLevel 30 }


gel2esw10gIP                                                    OBJECT IDENTIFIER ::= { gel2esw10gSystem 4 }

gel2esw10gIPv4                                                  OBJECT IDENTIFIER ::= { gel2esw10gIP 1 }

gel2esw10gIPv4Configured                                                  OBJECT IDENTIFIER ::= { gel2esw10gIPv4 1 }

gel2esw10gIpv4DHCPClient OBJECT-TYPE
   SYNTAX      INTEGER (0|1)
   MAX-ACCESS  read-write
   STATUS      current
   DESCRIPTION
       "default:0
       0: disable
       1: enable"
   ::= { gel2esw10gIPv4Configured 1 }

gel2esw10gIPv4Address OBJECT-TYPE
   SYNTAX      IpAddress
   MAX-ACCESS  read-write
   STATUS      current
   DESCRIPTION
       ""
   ::= { gel2esw10gIPv4Configured 2 }

gel2esw10gIPv4Mask OBJECT-TYPE
   SYNTAX      IpAddress
   MAX-ACCESS  read-write
   STATUS      current
   DESCRIPTION
       ""
   ::= { gel2esw10gIPv4Configured 3 }

gel2esw10gIPv4Router OBJECT-TYPE
   SYNTAX      IpAddress
   MAX-ACCESS  read-write
   STATUS      current
   DESCRIPTION
       ""
   ::= { gel2esw10gIPv4Configured 4 }

gel2esw10gIPv4VLANId OBJECT-TYPE
   SYNTAX      INTEGER (1..4094)
   MAX-ACCESS  read-write
   STATUS      current
   DESCRIPTION
       "default:1"
   ::= { gel2esw10gIPv4Configured 5 }

gel2esw10gIPv4DNSServer OBJECT-TYPE
   SYNTAX      IpAddress
   MAX-ACCESS  read-write
   STATUS      current
   DESCRIPTION
       ""
   ::= { gel2esw10gIPv4Configured 6 }

gel2esw10gIPv4DNSProxy OBJECT-TYPE
   SYNTAX      INTEGER (0|1)
   MAX-ACCESS  read-write
   STATUS      current
   DESCRIPTION
       " "
   ::= { gel2esw10gIPv4Configured 7 }

gel2esw10gIPv4Current                                                  OBJECT IDENTIFIER ::= { gel2esw10gIPv4 2 }

gel2esw10gIpv4CurrentDHCPClient OBJECT-TYPE
   SYNTAX      INTEGER (0|1)
   MAX-ACCESS  read-write
   STATUS      current
   DESCRIPTION
       "default:0
       0: none (for read)
       1: renew"
   ::= { gel2esw10gIPv4Current 1 }

gel2esw10gIPv4CurrentAddress OBJECT-TYPE
   SYNTAX      IpAddress
   MAX-ACCESS  read-only
   STATUS      current
   DESCRIPTION
       ""
   ::= { gel2esw10gIPv4Current 2 }

gel2esw10gIPv4CurrentMask OBJECT-TYPE
   SYNTAX      IpAddress
   MAX-ACCESS  read-only
   STATUS      current
   DESCRIPTION
       ""
   ::= { gel2esw10gIPv4Current 3 }

gel2esw10gIPv4CurrentRouter OBJECT-TYPE
   SYNTAX      IpAddress
   MAX-ACCESS  read-only
   STATUS      current
   DESCRIPTION
       ""
   ::= { gel2esw10gIPv4Current 4 }

gel2esw10gIPv4CurrentVLANId OBJECT-TYPE
   SYNTAX      INTEGER (1..4094)
   MAX-ACCESS  read-only
   STATUS      current
   DESCRIPTION
       "default:1"
   ::= { gel2esw10gIPv4Current 5 }

gel2esw10gIPv4CurrentDNSServer OBJECT-TYPE
   SYNTAX      IpAddress
   MAX-ACCESS  read-only
   STATUS      current
   DESCRIPTION
       ""
   ::= { gel2esw10gIPv4Current 6 }


gel2esw10gIPv6                                                  OBJECT IDENTIFIER ::= { gel2esw10gIP 2 }

gel2esw10gIPv6Configured                                                  OBJECT IDENTIFIER ::= { gel2esw10gIPv6 1 }

gel2esw10gIpv6AutoConfiguration OBJECT-TYPE
   SYNTAX      INTEGER (0|1)
   MAX-ACCESS  read-write
   STATUS      current
   DESCRIPTION
       "default:0
       0: disable
       1: enable"
   ::= { gel2esw10gIPv6Configured 1 }

gel2esw10gIpv6Address OBJECT-TYPE
   SYNTAX      DisplayString (SIZE (0..30))
   MAX-ACCESS  read-write
   STATUS      current
   DESCRIPTION
       ""
   ::= { gel2esw10gIPv6Configured 2 }

gel2esw10gIpv6Prefix OBJECT-TYPE
   SYNTAX      INTEGER (1..128)
   MAX-ACCESS  read-write
   STATUS      current
   DESCRIPTION
       "default: 96"
   ::= { gel2esw10gIPv6Configured 3 }

gel2esw10gIpv6Router OBJECT-TYPE
   SYNTAX      DisplayString (SIZE (0..30))
   MAX-ACCESS  read-write
   STATUS      current
   DESCRIPTION
       " "
   ::= { gel2esw10gIPv6Configured 4 }

gel2esw10gIPv6Current                                                  OBJECT IDENTIFIER ::= { gel2esw10gIPv6 2 }

gel2esw10gIpv6CurrentAutoConfiguration OBJECT-TYPE
   SYNTAX      INTEGER (0|1)
   MAX-ACCESS  read-only
   STATUS      current
   DESCRIPTION
       "default:0
       0: disable
       1: enable"
   ::= { gel2esw10gIPv6Current 1 }

gel2esw10gIpv6CurrentAddress OBJECT-TYPE
   SYNTAX      DisplayString (SIZE (0..30))
   MAX-ACCESS  read-only
   STATUS      current
   DESCRIPTION
       ""
   ::= { gel2esw10gIPv6Current 2 }


gel2esw10gIpv6CurrentLinkLocalAddress OBJECT-TYPE
   SYNTAX      DisplayString(SIZE (0..30))
   MAX-ACCESS  read-only
   STATUS      current
   DESCRIPTION
       ""
   ::= { gel2esw10gIPv6Current 3 }


gel2esw10gIpv6CurrentPrefix OBJECT-TYPE
   SYNTAX      INTEGER (1..128)
   MAX-ACCESS  read-only
   STATUS      current
   DESCRIPTION
       ""
   ::= { gel2esw10gIPv6Current 4 }

gel2esw10gIpv6CurrentRouter OBJECT-TYPE
   SYNTAX      DisplayString (SIZE (0..30))
   MAX-ACCESS  read-only
   STATUS      current
   DESCRIPTION
       " "
   ::= { gel2esw10gIPv6Current 5 }

gel2esw10gSyslog                                                OBJECT IDENTIFIER ::= { gel2esw10gSystem 5 }

gel2esw10gSyslogConf                                            OBJECT IDENTIFIER ::= { gel2esw10gSyslog 1 }

gel2esw10gServerMode OBJECT-TYPE
   SYNTAX      INTEGER (0|1)
   MAX-ACCESS  read-write
   STATUS      current
   DESCRIPTION
       "default: 0
       0: disable
       1: enable "
   ::= { gel2esw10gSyslogConf 1 }

gel2esw10gServerAddress1 OBJECT-TYPE
   SYNTAX      IpAddress
   MAX-ACCESS  read-write
   STATUS      current
   DESCRIPTION
       " "
   ::= { gel2esw10gSyslogConf 2 }

gel2esw10gServerAddress2 OBJECT-TYPE
   SYNTAX      IpAddress
   MAX-ACCESS  read-write
   STATUS      current
   DESCRIPTION
       " "
   ::= { gel2esw10gSyslogConf 3 }

gel2esw10gSyslogLevel OBJECT-TYPE
   SYNTAX      INTEGER(0..7)
   MAX-ACCESS  read-write
   STATUS      current
   DESCRIPTION
       "default: 6 (Info)
       0: Emergency
       1: Alert
       2: Critical
       3: Error
       4: Warning
       5: Notice
       6: Info
       7: Debug"
   ::= { gel2esw10gSyslogConf 4 }

gel2esw10gSyslogDetailedInfo                                    OBJECT IDENTIFIER ::= { gel2esw10gSyslog 2 }

gel2esw10gSyslogDetailedInfoClear OBJECT-TYPE
   SYNTAX      INTEGER(0|1)
   MAX-ACCESS  read-write
   STATUS      current
   DESCRIPTION
      "default: 0
       0 : None  (read only)
       1 : Clear Syslog"
   ::= { gel2esw10gSyslogDetailedInfo 1 }

gel2esw10gSyslogDetailedInfoTable OBJECT-TYPE
  SYNTAX      SEQUENCE OF GEL2ESW10GSyslogDetailedInfoEntry
  MAX-ACCESS  not-accessible
  STATUS      current
  DESCRIPTION
           " "
       ::= { gel2esw10gSyslogDetailedInfo 2 }

gel2esw10gSyslogDetailedInfoEntry OBJECT-TYPE
   SYNTAX      GEL2ESW10GSyslogDetailedInfoEntry
   MAX-ACCESS  not-accessible
   STATUS      current
   DESCRIPTION
           ""
   INDEX    { gel2esw10gSyslogDetailedInfoIndex  }
   ::= { gel2esw10gSyslogDetailedInfoTable 1 }

GEL2ESW10GSyslogDetailedInfoEntry ::= SEQUENCE {
   gel2esw10gSyslogDetailedInfoIndex       INTEGER,
   gel2esw10gSyslogDetailedInfoLevel       DisplayString,
   gel2esw10gSyslogDetailedInfoTime        DisplayString,
   gel2esw10gSyslogDetailedInfoMessage     DisplayString
}

gel2esw10gSyslogDetailedInfoIndex OBJECT-TYPE
   SYNTAX      INTEGER (1..1024)
   MAX-ACCESS  not-accessible
   STATUS      current
   DESCRIPTION
       " "
   ::= { gel2esw10gSyslogDetailedInfoEntry 1 }
   
gel2esw10gSyslogDetailedInfoLevel OBJECT-TYPE
   SYNTAX      DisplayString
   MAX-ACCESS  read-only
   STATUS      current
   DESCRIPTION
       " "
   ::= { gel2esw10gSyslogDetailedInfoEntry 2 }

gel2esw10gSyslogDetailedInfoTime OBJECT-TYPE
   SYNTAX      DisplayString(SIZE (0..20))
   MAX-ACCESS  read-only
   STATUS      current
   DESCRIPTION
       " "
   ::= { gel2esw10gSyslogDetailedInfoEntry 3 }

gel2esw10gSyslogDetailedInfoMessage OBJECT-TYPE
   SYNTAX      DisplayString
   MAX-ACCESS  read-only
   STATUS      current
   DESCRIPTION
       " "
   ::= { gel2esw10gSyslogDetailedInfoEntry 4 }


gel2esw10gSnmp                                                OBJECT IDENTIFIER ::= { gel2esw10gSystem 6 }

gel2esw10gSnmpConf                                            OBJECT IDENTIFIER ::= { gel2esw10gSnmp 1 }

gel2esw10gGetCommunity OBJECT-TYPE
   SYNTAX       DisplayString
   MAX-ACCESS   read-write
   STATUS       current
   DESCRIPTION
       "Get/Set the get-community of the SNMP."
   ::= { gel2esw10gSnmpConf 1 }

gel2esw10gSetCommunityMode OBJECT-TYPE
   SYNTAX       INTEGER(0|1) 
   MAX-ACCESS   read-write
   STATUS       current
   DESCRIPTION
       "Get/Set the set-community mode of the SNMP.
        default : 1, 0: disable, 1: enable. "
   ::= { gel2esw10gSnmpConf 2 }

gel2esw10gSetCommunity OBJECT-TYPE
   SYNTAX       DisplayString
   MAX-ACCESS   read-write
   STATUS       current
   DESCRIPTION
       "Get/Set the set-community of the SNMP."
   ::= { gel2esw10gSnmpConf 3 }

gel2esw10gTrapHostConfTable OBJECT-TYPE
   SYNTAX      SEQUENCE OF GEL2ESW10GTrapHostConfEntry
   MAX-ACCESS  not-accessible
   STATUS      current
   DESCRIPTION
       "A list of trap host entry. The numbers of entries are given by the value of gel2esw10gTrapHostConfNumber."
   ::= { gel2esw10gSnmpConf 4 }
   
gel2esw10gTrapHostConfEntry OBJECT-TYPE
   SYNTAX      GEL2ESW10GTrapHostConfEntry
   MAX-ACCESS  not-accessible
   STATUS      current
   DESCRIPTION
       "This is the entry information for trap host."
   INDEX    { gel2esw10gTrapHostConfIndex  }
   ::= { gel2esw10gTrapHostConfTable 1 }

GEL2ESW10GTrapHostConfEntry ::= SEQUENCE {
    gel2esw10gTrapHostConfIndex             INTEGER,
    gel2esw10gTrapHostConfVersion           INTEGER,
    gel2esw10gTrapHostConfIPType            INTEGER,
    gel2esw10gTrapHostConfIP                DisplayString,
    gel2esw10gTrapHostConfPort              INTEGER,
    gel2esw10gTrapHostConfCommunity         DisplayString,
    gel2esw10gTrapHostConfSeverityLevel     INTEGER,
    gel2esw10gTrapHostConfSecurityLevel     INTEGER,
    gel2esw10gTrapHostConfAuthPtc           INTEGER,
    gel2esw10gTrapHostConfAuthPassword      DisplayString,
    gel2esw10gTrapHostConfPrivPtc           INTEGER,
    gel2esw10gTrapHostConfPrivPassword      DisplayString,
    gel2esw10gTrapHostConfCurrentMode       INTEGER
}
   
gel2esw10gTrapHostConfIndex OBJECT-TYPE
   SYNTAX      INTEGER (1..6)
   MAX-ACCESS  not-accessible
   STATUS      current
   DESCRIPTION
       " The index of the trap host entry. "
   ::= { gel2esw10gTrapHostConfEntry 1 }

gel2esw10gTrapHostConfVersion OBJECT-TYPE
   SYNTAX       INTEGER(2..3)
   MAX-ACCESS   read-write
   STATUS       current
   DESCRIPTION
       "The version of the Trap PDU. Version : 2(SNMPv2c), 3(SNMPv3)"
   ::= { gel2esw10gTrapHostConfEntry 2 }

gel2esw10gTrapHostConfIPType OBJECT-TYPE
   SYNTAX       INTEGER(4|6)
   MAX-ACCESS   read-write
   STATUS       current
   DESCRIPTION
       "Server IP Type. Default: 4,
        4 : IPv4,
        6 : IPv6."
   ::= { gel2esw10gTrapHostConfEntry 3 }

gel2esw10gTrapHostConfIP OBJECT-TYPE
   SYNTAX       DisplayString
   MAX-ACCESS   read-write
   STATUS       current
   DESCRIPTION
       "This is the IP of the trap host."
   ::= { gel2esw10gTrapHostConfEntry 4 }

gel2esw10gTrapHostConfPort OBJECT-TYPE
   SYNTAX       INTEGER(1..65535)
   MAX-ACCESS   read-write
   STATUS       current
   DESCRIPTION
       "This is the receiving-port number of the trap host.
        range : 1 - 65535."
   ::= { gel2esw10gTrapHostConfEntry 5 }

gel2esw10gTrapHostConfCommunity OBJECT-TYPE
   SYNTAX       DisplayString (SIZE (1..32))
   MAX-ACCESS   read-write
   STATUS       current
   DESCRIPTION
       "The community/security name for the trap PDU."
   ::= { gel2esw10gTrapHostConfEntry 6 }

gel2esw10gTrapHostConfSeverityLevel	OBJECT-TYPE
   SYNTAX       INTEGER(0..7)
   MAX-ACCESS   read-write
   STATUS       current
   DESCRIPTION
       "The Severity Level.
        0 : Emerg, 1 : Alert, 2 : Crit, 3 : Error, 4 : Warning, 5 : Notice, 6 : Info, 7 : Debug."
	::= { gel2esw10gTrapHostConfEntry 7 }

gel2esw10gTrapHostConfSecurityLevel	OBJECT-TYPE
   SYNTAX       INTEGER(1..3)
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gel2esw10gTrapHostConfEntry 8 }

gel2esw10gTrapHostConfAuthPtc	OBJECT-TYPE
   SYNTAX       INTEGER(1..2)
   MAX-ACCESS   read-write
   STATUS       current
   DESCRIPTION
       "Authentication Protocol, there are SHA and MD5 supported presently.
        1 : MD5, 2 : SHA."
	::= { gel2esw10gTrapHostConfEntry 9 }

gel2esw10gTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gel2esw10gTrapHostConfEntry 10 }

gel2esw10gTrapHostConfPrivPtc	OBJECT-TYPE
   SYNTAX       INTEGER(1)
   MAX-ACCESS   read-write
   STATUS       current
   DESCRIPTION
       "This is the Privacy Protocol, which is used in AuthPriv. Only supports DES.
        An empty string will be returned if the security level is not 3(AuthPriv).
        1 : DES."
	::= { gel2esw10gTrapHostConfEntry 11 }

gel2esw10gTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gel2esw10gTrapHostConfEntry 12 }

gel2esw10gTrapHostConfCurrentMode OBJECT-TYPE
   SYNTAX       INTEGER(0..2)
   MAX-ACCESS   read-write
   STATUS       current
   DESCRIPTION
       "0:Empty, 1:Active mode, 2:Edit mode, 3:Delete."
   ::= { gel2esw10gTrapHostConfEntry 13 }


----------------------------------------------------------------------------------------------------

gel2esw10gConfiguration                                         OBJECT IDENTIFIER ::= { gel2esw10gProductId 2 }

gel2esw10gPort                                                  OBJECT IDENTIFIER ::= { gel2esw10gConfiguration 1 }

gel2esw10gPortConfigurationTable OBJECT-TYPE
   SYNTAX      SEQUENCE OF GEL2ESW10GPortConfigurationEntry
   MAX-ACCESS  not-accessible
   STATUS      current
   DESCRIPTION
       " Show port configurations. "
   ::= { gel2esw10gPort 1 }

gel2esw10gPortConfigurationEntry OBJECT-TYPE
   SYNTAX      GEL2ESW10GPortConfigurationEntry
   MAX-ACCESS  not-accessible
   STATUS      current
   DESCRIPTION
       ""
   INDEX    { gel2esw10gPortConfPort  }
   ::= { gel2esw10gPortConfigurationTable 1 }

GEL2ESW10GPortConfigurationEntry ::= SEQUENCE {
   gel2esw10gPortConfPort                     INTEGER,
   gel2esw10gPortConfPortMedia                DisplayString,
   gel2esw10gPortConfLink                     DisplayString,
   gel2esw10gPortConfCurrentSpeed             DisplayString,
   gel2esw10gPortConfSpeed                    INTEGER,
   gel2esw10gPortConfCurrentFlowControlRx     INTEGER,
   gel2esw10gPortConfCurrentFlowControlTx     INTEGER,
   gel2esw10gPortConfFlowControl              INTEGER,
   gel2esw10gPortConfMaxFrameSize             INTEGER,
   gel2esw10gPortConfExcessiveCollisionMode   INTEGER,
   gel2esw10gPortConfPowerControl             INTEGER,
   gel2esw10gPortConfDescription              DisplayString
}

gel2esw10gPortConfPort OBJECT-TYPE
   SYNTAX      INTEGER (1..4095)
   MAX-ACCESS  not-accessible
   STATUS      current
   DESCRIPTION
       " port, range : 1 - port number. "
   ::= { gel2esw10gPortConfigurationEntry 1 }

gel2esw10gPortConfPortMedia OBJECT-TYPE
   SYNTAX      DisplayString(SIZE (1..4))
   MAX-ACCESS  read-only
   STATUS      current
   DESCRIPTION
       " Show port media. "
   ::= { gel2esw10gPortConfigurationEntry 2 }

gel2esw10gPortConfLink OBJECT-TYPE
   SYNTAX      DisplayString(SIZE (2..4))
   MAX-ACCESS  read-only
   STATUS      current
   DESCRIPTION
       " The current link state. "
   ::= { gel2esw10gPortConfigurationEntry 3 }

gel2esw10gPortConfCurrentSpeed OBJECT-TYPE
   SYNTAX      DisplayString(SIZE (6..12))
   MAX-ACCESS  read-only
   STATUS      current
   DESCRIPTION
       " The current link speed of the port. "
   ::= { gel2esw10gPortConfigurationEntry 4 }

gel2esw10gPortConfSpeed OBJECT-TYPE
   SYNTAX      INTEGER (0..11)
   MAX-ACCESS  read-write
   STATUS      current
   DESCRIPTION
       "default: 1,
        0: disable state, 
        1: auto, 
        2: 10 Half, 
        3: 10 Full, 
        4: 100 Half, 
        5: 100 Full, 
        6: 1G full, 
        only 'Dual Media' port have 7-11 option. 
        Dual Media port default: 7,  
        7: SFP_Auto_AMS, 
        8: 100FX_AMS, 
        9: 1000X_AMS, 
        10: 100FX, 
        11: 1000X "
   ::= { gel2esw10gPortConfigurationEntry 5 }

gel2esw10gPortConfCurrentFlowControlRx OBJECT-TYPE
   SYNTAX      INTEGER (0|1)
   MAX-ACCESS  read-only
   STATUS      current
   DESCRIPTION
       "0: disable
        1: enable
        2: not support.  "
   ::= { gel2esw10gPortConfigurationEntry 6 }

gel2esw10gPortConfCurrentFlowControlTx OBJECT-TYPE
   SYNTAX      INTEGER (0|1)
   MAX-ACCESS  read-only
   STATUS      current
   DESCRIPTION
       "0: disable
        1: enable
        2: not support.  "
   ::= { gel2esw10gPortConfigurationEntry 7 }

gel2esw10gPortConfFlowControl OBJECT-TYPE
   SYNTAX      INTEGER (0|1)
   MAX-ACCESS  read-write
   STATUS      current
   DESCRIPTION
       "default: 0,
        0: disable
        1: enable
        2: not support. "
   ::= { gel2esw10gPortConfigurationEntry 8 }

gel2esw10gPortConfMaxFrameSize OBJECT-TYPE
   SYNTAX      INTEGER (1518..9600)
   MAX-ACCESS  read-write
   STATUS      current
   DESCRIPTION
       "default: 9600 , range : 1518 - 9600 "
   ::= { gel2esw10gPortConfigurationEntry 9 }

gel2esw10gPortConfExcessiveCollisionMode OBJECT-TYPE
   SYNTAX      INTEGER (0|1)
   MAX-ACCESS  read-write
   STATUS      current
   DESCRIPTION
       "default: 0,
        Excessive Collision Mode : 
        0: Discard,
        1: Restart, 
        2: not support.
       "
   ::= { gel2esw10gPortConfigurationEntry 10 }

gel2esw10gPortConfPowerControl OBJECT-TYPE
   SYNTAX      INTEGER (0..3)
   MAX-ACCESS  read-write
   STATUS      current
   DESCRIPTION
       "default: 0,
        PowerControl :
        0: disable,
        1: Actiphy, 
        2: Dynamic (perfectReach),
        3: Enable,
        4: not support.
       "
   ::= { gel2esw10gPortConfigurationEntry 11 }

gel2esw10gPortConfDescription OBJECT-TYPE
   SYNTAX      DisplayString
   MAX-ACCESS  read-write
   STATUS      current
   DESCRIPTION
       " Interface specific description.
         Up to 47 characters describing this interface. "
   ::= { gel2esw10gPortConfigurationEntry 12 }


gel2esw10gPortTrafficStatisticsTable OBJECT-TYPE
   SYNTAX      SEQUENCE OF GEL2ESW10GPortTrafficStatisticsEntry
   MAX-ACCESS  not-accessible
   STATUS      current
   DESCRIPTION
       " "
   ::= { gel2esw10gPort 2 }

gel2esw10gPortTrafficStatisticsEntry OBJECT-TYPE
   SYNTAX      GEL2ESW10GPortTrafficStatisticsEntry
   MAX-ACCESS  not-accessible
   STATUS      current
   DESCRIPTION
       ""
   INDEX    { gel2esw10gPortTrafficStatisticsPort  }
   ::= { gel2esw10gPortTrafficStatisticsTable 1 }

GEL2ESW10GPortTrafficStatisticsEntry ::= SEQUENCE {
   gel2esw10gPortTrafficStatisticsPort          INTEGER,
   gel2esw10gPortTrafficStatisticsClear         INTEGER,
   gel2esw10gPortTrafficRxPackets               Counter64,
   gel2esw10gPortTrafficRxOctets                Counter64,
   gel2esw10gPortTrafficRxUnicast               Counter64,
   gel2esw10gPortTrafficRxMulticast             Counter64,
   gel2esw10gPortTrafficRxBroadcast             Counter64,
   gel2esw10gPortTrafficRxPause                 Counter64,
   gel2esw10gPortTrafficRx64Bytes               Counter64,
   gel2esw10gPortTrafficRx65to127Bytes          Counter64,
   gel2esw10gPortTrafficRx128to255Bytes         Counter64,
   gel2esw10gPortTrafficRx256to511Bytes         Counter64,
   gel2esw10gPortTrafficRx512to1023Bytes        Counter64,
   gel2esw10gPortTrafficRx1024to1526Bytes       Counter64,
   gel2esw10gPortTrafficRxExceecd1527Bytes      Counter64,
   gel2esw10gPortTrafficRxQ0                    Counter64,
   gel2esw10gPortTrafficRxQ1                    Counter64,
   gel2esw10gPortTrafficRxQ2                    Counter64,
   gel2esw10gPortTrafficRxQ3                    Counter64,
   gel2esw10gPortTrafficRxQ4                    Counter64,
   gel2esw10gPortTrafficRxQ5                    Counter64,
   gel2esw10gPortTrafficRxQ6                    Counter64,
   gel2esw10gPortTrafficRxQ7                    Counter64,
   gel2esw10gPortTrafficRxDrops                 Counter64,
   gel2esw10gPortTrafficRxCRCorAlignment        Counter64,
   gel2esw10gPortTrafficRxUndersize             Counter64,
   gel2esw10gPortTrafficRxOversize              Counter64,
   gel2esw10gPortTrafficRxFragments             Counter64,
   gel2esw10gPortTrafficRxJabber                Counter64,
   gel2esw10gPortTrafficRxFiltered              Counter64,
   gel2esw10gPortTrafficTxPackets               Counter64,
   gel2esw10gPortTrafficTxOctets                Counter64,
   gel2esw10gPortTrafficTxUnicast               Counter64,
   gel2esw10gPortTrafficTxMulticast             Counter64,
   gel2esw10gPortTrafficTxBroadcast             Counter64,
   gel2esw10gPortTrafficTxPause                 Counter64,
   gel2esw10gPortTrafficTx64Bytes               Counter64,
   gel2esw10gPortTrafficTx65to127Bytes          Counter64,
   gel2esw10gPortTrafficTx128to255Bytes         Counter64,
   gel2esw10gPortTrafficTx256to511Bytes         Counter64,
   gel2esw10gPortTrafficTx512to1023Bytes        Counter64,
   gel2esw10gPortTrafficTx1024to1526Bytes       Counter64,
   gel2esw10gPortTrafficTxExceecd1527Bytes      Counter64,
   gel2esw10gPortTrafficTxQ0                    Counter64,
   gel2esw10gPortTrafficTxQ1                    Counter64,
   gel2esw10gPortTrafficTxQ2                    Counter64,
   gel2esw10gPortTrafficTxQ3                    Counter64,
   gel2esw10gPortTrafficTxQ4                    Counter64,
   gel2esw10gPortTrafficTxQ5                    Counter64,
   gel2esw10gPortTrafficTxQ6                    Counter64,
   gel2esw10gPortTrafficTxQ7                    Counter64,
   gel2esw10gPortTrafficTxDrops                 Counter64,
   gel2esw10gPortTrafficTxLateOrExcColl         Counter64
}

gel2esw10gPortTrafficStatisticsPort OBJECT-TYPE
   SYNTAX      INTEGER (1..4095)
   MAX-ACCESS  not-accessible
   STATUS      current
   DESCRIPTION
       " "
   ::= { gel2esw10gPortTrafficStatisticsEntry 1 }

gel2esw10gPortTrafficStatisticsClear OBJECT-TYPE
   SYNTAX      INTEGER(0|1)
   MAX-ACCESS  read-write
   STATUS      current
   DESCRIPTION
       " "
   ::= { gel2esw10gPortTrafficStatisticsEntry 2 }

gel2esw10gPortTrafficRxPackets OBJECT-TYPE
   SYNTAX      Counter64
   MAX-ACCESS  read-only
   STATUS      current
   DESCRIPTION
       " "
   ::= { gel2esw10gPortTrafficStatisticsEntry 3 }

gel2esw10gPortTrafficRxOctets OBJECT-TYPE
   SYNTAX      Counter64
   MAX-ACCESS  read-only
   STATUS      current
   DESCRIPTION
       " "
   ::= { gel2esw10gPortTrafficStatisticsEntry 4 }

gel2esw10gPortTrafficRxUnicast OBJECT-TYPE
   SYNTAX      Counter64
   MAX-ACCESS  read-only
   STATUS      current
   DESCRIPTION
       " "
   ::= { gel2esw10gPortTrafficStatisticsEntry 5 }

gel2esw10gPortTrafficRxMulticast OBJECT-TYPE
   SYNTAX      Counter64
   MAX-ACCESS  read-only
   STATUS      current
   DESCRIPTION
       " "
   ::= { gel2esw10gPortTrafficStatisticsEntry 6 }

gel2esw10gPortTrafficRxBroadcast OBJECT-TYPE
   SYNTAX      Counter64
   MAX-ACCESS  read-only
   STATUS      current
   DESCRIPTION
       " "
   ::= { gel2esw10gPortTrafficStatisticsEntry 7 }

gel2esw10gPortTrafficRxPause OBJECT-TYPE
   SYNTAX      Counter64
   MAX-ACCESS  read-only
   STATUS      current
   DESCRIPTION
       " "
   ::= { gel2esw10gPortTrafficStatisticsEntry 8 }

gel2esw10gPortTrafficRx64Bytes OBJECT-TYPE
   SYNTAX      Counter64
   MAX-ACCESS  read-only
   STATUS      current
   DESCRIPTION
       " "
   ::= { gel2esw10gPortTrafficStatisticsEntry 9 }

gel2esw10gPortTrafficRx65to127Bytes OBJECT-TYPE
   SYNTAX      Counter64
   MAX-ACCESS  read-only
   STATUS      current
   DESCRIPTION
       " "
   ::= { gel2esw10gPortTrafficStatisticsEntry 10 }

gel2esw10gPortTrafficRx128to255Bytes OBJECT-TYPE
   SYNTAX      Counter64
   MAX-ACCESS  read-only
   STATUS      current
   DESCRIPTION
       " "
   ::= { gel2esw10gPortTrafficStatisticsEntry 11 }

gel2esw10gPortTrafficRx256to511Bytes OBJECT-TYPE
   SYNTAX      Counter64
   MAX-ACCESS  read-only
   STATUS      current
   DESCRIPTION
       " "
   ::= { gel2esw10gPortTrafficStatisticsEntry 12 }

gel2esw10gPortTrafficRx512to1023Bytes OBJECT-TYPE
   SYNTAX      Counter64
   MAX-ACCESS  read-only
   STATUS      current
   DESCRIPTION
       " "
   ::= { gel2esw10gPortTrafficStatisticsEntry 13 }

gel2esw10gPortTrafficRx1024to1526Bytes OBJECT-TYPE
   SYNTAX      Counter64
   MAX-ACCESS  read-only
   STATUS      current
   DESCRIPTION
       " "
   ::= { gel2esw10gPortTrafficStatisticsEntry 14 }

gel2esw10gPortTrafficRxExceecd1527Bytes OBJECT-TYPE
   SYNTAX      Counter64
   MAX-ACCESS  read-only
   STATUS      current
   DESCRIPTION
       " "
   ::= { gel2esw10gPortTrafficStatisticsEntry 15 }

gel2esw10gPortTrafficRxQ0 OBJECT-TYPE
   SYNTAX      Counter64
   MAX-ACCESS  read-only
   STATUS      current
   DESCRIPTION
       " "
   ::= { gel2esw10gPortTrafficStatisticsEntry 16 }

gel2esw10gPortTrafficRxQ1 OBJECT-TYPE
   SYNTAX      Counter64
   MAX-ACCESS  read-only
   STATUS      current
   DESCRIPTION
       " "
   ::= { gel2esw10gPortTrafficStatisticsEntry 17 }

gel2esw10gPortTrafficRxQ2 OBJECT-TYPE
   SYNTAX      Counter64
   MAX-ACCESS  read-only
   STATUS      current
   DESCRIPTION
       " "
   ::= { gel2esw10gPortTrafficStatisticsEntry 18 }

gel2esw10gPortTrafficRxQ3 OBJECT-TYPE
   SYNTAX      Counter64
   MAX-ACCESS  read-only
   STATUS      current
   DESCRIPTION
       " "
   ::= { gel2esw10gPortTrafficStatisticsEntry 19 }

gel2esw10gPortTrafficRxQ4 OBJECT-TYPE
   SYNTAX      Counter64
   MAX-ACCESS  read-only
   STATUS      current
   DESCRIPTION
       " "
   ::= { gel2esw10gPortTrafficStatisticsEntry 20 }

gel2esw10gPortTrafficRxQ5 OBJECT-TYPE
   SYNTAX      Counter64
   MAX-ACCESS  read-only
   STATUS      current
   DESCRIPTION
       " "
   ::= { gel2esw10gPortTrafficStatisticsEntry 21 }

gel2esw10gPortTrafficRxQ6 OBJECT-TYPE
   SYNTAX      Counter64
   MAX-ACCESS  read-only
   STATUS      current
   DESCRIPTION
       " "
   ::= { gel2esw10gPortTrafficStatisticsEntry 22 }

gel2esw10gPortTrafficRxQ7 OBJECT-TYPE
   SYNTAX      Counter64
   MAX-ACCESS  read-only
   STATUS      current
   DESCRIPTION
       " "
   ::= { gel2esw10gPortTrafficStatisticsEntry 23 }

gel2esw10gPortTrafficRxDrops OBJECT-TYPE
   SYNTAX      Counter64
   MAX-ACCESS  read-only
   STATUS      current
   DESCRIPTION
       " "
   ::= { gel2esw10gPortTrafficStatisticsEntry 24 }

gel2esw10gPortTrafficRxCRCorAlignment OBJECT-TYPE
   SYNTAX      Counter64
   MAX-ACCESS  read-only
   STATUS      current
   DESCRIPTION
       " "
   ::= { gel2esw10gPortTrafficStatisticsEntry 25 }

gel2esw10gPortTrafficRxUndersize OBJECT-TYPE
   SYNTAX      Counter64
   MAX-ACCESS  read-only
   STATUS      current
   DESCRIPTION
       " "
   ::= { gel2esw10gPortTrafficStatisticsEntry 26 }

gel2esw10gPortTrafficRxOversize OBJECT-TYPE
   SYNTAX      Counter64
   MAX-ACCESS  read-only
   STATUS      current
   DESCRIPTION
       " "
   ::= { gel2esw10gPortTrafficStatisticsEntry 27 }

gel2esw10gPortTrafficRxFragments OBJECT-TYPE
   SYNTAX      Counter64
   MAX-ACCESS  read-only
   STATUS      current
   DESCRIPTION
       " "
   ::= { gel2esw10gPortTrafficStatisticsEntry 28 }

gel2esw10gPortTrafficRxJabber OBJECT-TYPE
   SYNTAX      Counter64
   MAX-ACCESS  read-only
   STATUS      current
   DESCRIPTION
       " "
   ::= { gel2esw10gPortTrafficStatisticsEntry 29 }

gel2esw10gPortTrafficRxFiltered OBJECT-TYPE
   SYNTAX      Counter64
   MAX-ACCESS  read-only
   STATUS      current
   DESCRIPTION
       " "
   ::= { gel2esw10gPortTrafficStatisticsEntry 30 }

gel2esw10gPortTrafficTxPackets OBJECT-TYPE
   SYNTAX      Counter64
   MAX-ACCESS  read-only
   STATUS      current
   DESCRIPTION
       " "
   ::= { gel2esw10gPortTrafficStatisticsEntry 31 }

gel2esw10gPortTrafficTxOctets OBJECT-TYPE
   SYNTAX      Counter64
   MAX-ACCESS  read-only
   STATUS      current
   DESCRIPTION
       " "
   ::= { gel2esw10gPortTrafficStatisticsEntry 32 }

gel2esw10gPortTrafficTxUnicast OBJECT-TYPE
   SYNTAX      Counter64
   MAX-ACCESS  read-only
   STATUS      current
   DESCRIPTION
       " "
   ::= { gel2esw10gPortTrafficStatisticsEntry 33 }

gel2esw10gPortTrafficTxMulticast OBJECT-TYPE
   SYNTAX      Counter64
   MAX-ACCESS  read-only
   STATUS      current
   DESCRIPTION
       " "
   ::= { gel2esw10gPortTrafficStatisticsEntry 34 }

gel2esw10gPortTrafficTxBroadcast OBJECT-TYPE
   SYNTAX      Counter64
   MAX-ACCESS  read-only
   STATUS      current
   DESCRIPTION
       " "
   ::= { gel2esw10gPortTrafficStatisticsEntry 35 }

gel2esw10gPortTrafficTxPause OBJECT-TYPE
   SYNTAX      Counter64
   MAX-ACCESS  read-only
   STATUS      current
   DESCRIPTION
       " "
   ::= { gel2esw10gPortTrafficStatisticsEntry 36 }

gel2esw10gPortTrafficTx64Bytes OBJECT-TYPE
   SYNTAX      Counter64
   MAX-ACCESS  read-only
   STATUS      current
   DESCRIPTION
       " "
   ::= { gel2esw10gPortTrafficStatisticsEntry 37 }

gel2esw10gPortTrafficTx65to127Bytes OBJECT-TYPE
   SYNTAX      Counter64
   MAX-ACCESS  read-only
   STATUS      current
   DESCRIPTION
       " "
   ::= { gel2esw10gPortTrafficStatisticsEntry 38 }

gel2esw10gPortTrafficTx128to255Bytes OBJECT-TYPE
   SYNTAX      Counter64
   MAX-ACCESS  read-only
   STATUS      current
   DESCRIPTION
       " "
   ::= { gel2esw10gPortTrafficStatisticsEntry 39 }

gel2esw10gPortTrafficTx256to511Bytes OBJECT-TYPE
   SYNTAX      Counter64
   MAX-ACCESS  read-only
   STATUS      current
   DESCRIPTION
       " "
   ::= { gel2esw10gPortTrafficStatisticsEntry 40 }

gel2esw10gPortTrafficTx512to1023Bytes OBJECT-TYPE
   SYNTAX      Counter64
   MAX-ACCESS  read-only
   STATUS      current
   DESCRIPTION
       " "
   ::= { gel2esw10gPortTrafficStatisticsEntry 41 }

gel2esw10gPortTrafficTx1024to1526Bytes OBJECT-TYPE
   SYNTAX      Counter64
   MAX-ACCESS  read-only
   STATUS      current
   DESCRIPTION
       " "
   ::= { gel2esw10gPortTrafficStatisticsEntry 42 }

gel2esw10gPortTrafficTxExceecd1527Bytes OBJECT-TYPE
   SYNTAX      Counter64
   MAX-ACCESS  read-only
   STATUS      current
   DESCRIPTION
       " "
   ::= { gel2esw10gPortTrafficStatisticsEntry 43 }

gel2esw10gPortTrafficTxQ0 OBJECT-TYPE
   SYNTAX      Counter64
   MAX-ACCESS  read-only
   STATUS      current
   DESCRIPTION
       " "
   ::= { gel2esw10gPortTrafficStatisticsEntry 44 }

gel2esw10gPortTrafficTxQ1 OBJECT-TYPE
   SYNTAX      Counter64
   MAX-ACCESS  read-only
   STATUS      current
   DESCRIPTION
       " "
   ::= { gel2esw10gPortTrafficStatisticsEntry 45 }

gel2esw10gPortTrafficTxQ2 OBJECT-TYPE
   SYNTAX      Counter64
   MAX-ACCESS  read-only
   STATUS      current
   DESCRIPTION
       " "
   ::= { gel2esw10gPortTrafficStatisticsEntry 46 }

gel2esw10gPortTrafficTxQ3 OBJECT-TYPE
   SYNTAX      Counter64
   MAX-ACCESS  read-only
   STATUS      current
   DESCRIPTION
       " "
   ::= { gel2esw10gPortTrafficStatisticsEntry 47 }

gel2esw10gPortTrafficTxQ4 OBJECT-TYPE
   SYNTAX      Counter64
   MAX-ACCESS  read-only
   STATUS      current
   DESCRIPTION
       " "
   ::= { gel2esw10gPortTrafficStatisticsEntry 48 }

gel2esw10gPortTrafficTxQ5 OBJECT-TYPE
   SYNTAX      Counter64
   MAX-ACCESS  read-only
   STATUS      current
   DESCRIPTION
       " "
   ::= { gel2esw10gPortTrafficStatisticsEntry 49 }

gel2esw10gPortTrafficTxQ6 OBJECT-TYPE
   SYNTAX      Counter64
   MAX-ACCESS  read-only
   STATUS      current
   DESCRIPTION
       " "
   ::= { gel2esw10gPortTrafficStatisticsEntry 50 }


gel2esw10gPortTrafficTxQ7 OBJECT-TYPE
   SYNTAX      Counter64
   MAX-ACCESS  read-only
   STATUS      current
   DESCRIPTION
       " "
   ::= { gel2esw10gPortTrafficStatisticsEntry 51 }

gel2esw10gPortTrafficTxDrops OBJECT-TYPE
   SYNTAX      Counter64
   MAX-ACCESS  read-only
   STATUS      current
   DESCRIPTION
       " "
   ::= { gel2esw10gPortTrafficStatisticsEntry 52 }

gel2esw10gPortTrafficTxLateOrExcColl OBJECT-TYPE
   SYNTAX      Counter64
   MAX-ACCESS  read-only
   STATUS      current
   DESCRIPTION
       " "
   ::= { gel2esw10gPortTrafficStatisticsEntry 53 }


gel2esw10gPortQoSStatistics                                     OBJECT IDENTIFIER ::= { gel2esw10gPort 3 }

gel2esw10gPortQoSStatisticsClear OBJECT-TYPE
   SYNTAX      INTEGER(0|1)
   MAX-ACCESS  read-only
   STATUS      current
   DESCRIPTION
       "default: 0
       0: none
       1: clear "
   ::= { gel2esw10gPortQoSStatistics 1 }

gel2esw10gPortQoSStatisticsTable OBJECT-TYPE
   SYNTAX      SEQUENCE OF GEL2ESW10GPortQoSStatisticsEntry
   MAX-ACCESS  not-accessible
   STATUS      current
   DESCRIPTION
       " "
   ::= { gel2esw10gPortQoSStatistics 2 }

gel2esw10gPortQoSStatisticsEntry OBJECT-TYPE
   SYNTAX      GEL2ESW10GPortQoSStatisticsEntry
   MAX-ACCESS  not-accessible
   STATUS      current
   DESCRIPTION
       ""
   INDEX    { gel2esw10gPortQoSStatisticsPort  }
   ::= { gel2esw10gPortQoSStatisticsTable 1 }

GEL2ESW10GPortQoSStatisticsEntry ::= SEQUENCE {
   gel2esw10gPortQoSStatisticsPort      INTEGER,
   gel2esw10gPortQoSQ0Rx                Counter64,
   gel2esw10gPortQoSQ0Tx                Counter64,
   gel2esw10gPortQoSQ1Rx                Counter64,
   gel2esw10gPortQoSQ1Tx                Counter64,
   gel2esw10gPortQoSQ2Rx                Counter64,
   gel2esw10gPortQoSQ2Tx                Counter64,
   gel2esw10gPortQoSQ3Rx                Counter64,
   gel2esw10gPortQoSQ3Tx                Counter64,
   gel2esw10gPortQoSQ4Rx                Counter64,
   gel2esw10gPortQoSQ4Tx                Counter64,
   gel2esw10gPortQoSQ5Rx                Counter64,
   gel2esw10gPortQoSQ5Tx                Counter64,
   gel2esw10gPortQoSQ6Rx                Counter64,
   gel2esw10gPortQoSQ6Tx                Counter64,
   gel2esw10gPortQoSQ7Rx                Counter64,
   gel2esw10gPortQoSQ7Tx                Counter64
}

gel2esw10gPortQoSStatisticsPort OBJECT-TYPE
   SYNTAX      INTEGER (1..4095)
   MAX-ACCESS  not-accessible
   STATUS      current
   DESCRIPTION
       " "
   ::= { gel2esw10gPortQoSStatisticsEntry 1 }

gel2esw10gPortQoSQ0Rx OBJECT-TYPE
   SYNTAX      Counter64
   MAX-ACCESS  read-only
   STATUS      current
   DESCRIPTION
       " "
   ::= { gel2esw10gPortQoSStatisticsEntry 2 }

gel2esw10gPortQoSQ0Tx OBJECT-TYPE
   SYNTAX      Counter64
   MAX-ACCESS  read-only
   STATUS      current
   DESCRIPTION
       " "
   ::= { gel2esw10gPortQoSStatisticsEntry 3 }

gel2esw10gPortQoSQ1Rx OBJECT-TYPE
   SYNTAX      Counter64
   MAX-ACCESS  read-only
   STATUS      current
   DESCRIPTION
       " "
   ::= { gel2esw10gPortQoSStatisticsEntry 4 }

gel2esw10gPortQoSQ1Tx OBJECT-TYPE
   SYNTAX      Counter64
   MAX-ACCESS  read-only
   STATUS      current
   DESCRIPTION
       " "
   ::= { gel2esw10gPortQoSStatisticsEntry 5 }

gel2esw10gPortQoSQ2Rx OBJECT-TYPE
   SYNTAX      Counter64
   MAX-ACCESS  read-only
   STATUS      current
   DESCRIPTION
       " "
   ::= { gel2esw10gPortQoSStatisticsEntry 6 }

gel2esw10gPortQoSQ2Tx OBJECT-TYPE
   SYNTAX      Counter64
   MAX-ACCESS  read-only
   STATUS      current
   DESCRIPTION
       " "
   ::= { gel2esw10gPortQoSStatisticsEntry 7 }

gel2esw10gPortQoSQ3Rx OBJECT-TYPE
   SYNTAX      Counter64
   MAX-ACCESS  read-only
   STATUS      current
   DESCRIPTION
       " "
   ::= { gel2esw10gPortQoSStatisticsEntry 8 }

gel2esw10gPortQoSQ3Tx OBJECT-TYPE
   SYNTAX      Counter64
   MAX-ACCESS  read-only
   STATUS      current
   DESCRIPTION
       " "
   ::= { gel2esw10gPortQoSStatisticsEntry 9 }

gel2esw10gPortQoSQ4Rx OBJECT-TYPE
   SYNTAX      Counter64
   MAX-ACCESS  read-only
   STATUS      current
   DESCRIPTION
       " "
   ::= { gel2esw10gPortQoSStatisticsEntry 10 }

gel2esw10gPortQoSQ4Tx OBJECT-TYPE
   SYNTAX      Counter64
   MAX-ACCESS  read-only
   STATUS      current
   DESCRIPTION
       " "
   ::= { gel2esw10gPortQoSStatisticsEntry 11 }

gel2esw10gPortQoSQ5Rx OBJECT-TYPE
   SYNTAX      Counter64
   MAX-ACCESS  read-only
   STATUS      current
   DESCRIPTION
       " "
   ::= { gel2esw10gPortQoSStatisticsEntry 12 }

gel2esw10gPortQoSQ5Tx OBJECT-TYPE
   SYNTAX      Counter64
   MAX-ACCESS  read-only
   STATUS      current
   DESCRIPTION
       " "
   ::= { gel2esw10gPortQoSStatisticsEntry 13 }

gel2esw10gPortQoSQ6Rx OBJECT-TYPE
   SYNTAX      Counter64
   MAX-ACCESS  read-only
   STATUS      current
   DESCRIPTION
       " "
   ::= { gel2esw10gPortQoSStatisticsEntry 14 }

gel2esw10gPortQoSQ6Tx OBJECT-TYPE
   SYNTAX      Counter64
   MAX-ACCESS  read-only
   STATUS      current
   DESCRIPTION
       " "
   ::= { gel2esw10gPortQoSStatisticsEntry 15 }

gel2esw10gPortQoSQ7Rx OBJECT-TYPE
   SYNTAX      Counter64
   MAX-ACCESS  read-only
   STATUS      current
   DESCRIPTION
       " "
   ::= { gel2esw10gPortQoSStatisticsEntry 16 }

gel2esw10gPortQoSQ7Tx OBJECT-TYPE
   SYNTAX      Counter64
   MAX-ACCESS  read-only
   STATUS      current
   DESCRIPTION
       " "
   ::= { gel2esw10gPortQoSStatisticsEntry 17 }

gel2esw10gSFPInfoTable OBJECT-TYPE
   SYNTAX      SEQUENCE OF GEL2ESW10GSFPInfoEntry
   MAX-ACCESS  not-accessible
   STATUS      current
   DESCRIPTION
       " "
   ::= { gel2esw10gPort 4 }

gel2esw10gSFPInfoEntry OBJECT-TYPE
   SYNTAX      GEL2ESW10GSFPInfoEntry
   MAX-ACCESS  not-accessible
   STATUS      current
   DESCRIPTION
       ""
   INDEX    { gel2esw10gSFPInfoIndex }
   ::= { gel2esw10gSFPInfoTable 1 }

GEL2ESW10GSFPInfoEntry ::= SEQUENCE {
   gel2esw10gSFPInfoIndex               INTEGER,
   gel2esw10gSFPInfoPort                DisplayString,
   gel2esw10gSFPConnectorType           DisplayString,
   gel2esw10gSFPFiberType               DisplayString,
   gel2esw10gSFPTxCentralWavelength     DisplayString,
   gel2esw10gSFPBaudRate                DisplayString,
   gel2esw10gSFPVendorOUI               DisplayString,
   gel2esw10gSFPVendorName              DisplayString,
   gel2esw10gSFPVendorPN                DisplayString,
   gel2esw10gSFPVendorRev               DisplayString,
   gel2esw10gSFPVendorSN                DisplayString,
   gel2esw10gSFPDateCode                DisplayString,
   gel2esw10gSFPTemperature             DisplayString,
   gel2esw10gSFPVcc                     DisplayString,
   gel2esw10gSFPMon1Bias                DisplayString,
   gel2esw10gSFPMon2TxPWR               DisplayString,
   gel2esw10gSFPMon3RxPWR               DisplayString
}

gel2esw10gSFPInfoIndex OBJECT-TYPE
   SYNTAX      INTEGER (1..4095)
   MAX-ACCESS  not-accessible
   STATUS      current
   DESCRIPTION
       " "
   ::= { gel2esw10gSFPInfoEntry 1 }

gel2esw10gSFPInfoPort OBJECT-TYPE
   SYNTAX      DisplayString
   MAX-ACCESS  read-only
   STATUS      current
   DESCRIPTION
       " "
   ::= { gel2esw10gSFPInfoEntry 2 }

gel2esw10gSFPConnectorType OBJECT-TYPE
   SYNTAX      DisplayString
   MAX-ACCESS  read-only
   STATUS      current
   DESCRIPTION
       " "
   ::= { gel2esw10gSFPInfoEntry 3 }

gel2esw10gSFPFiberType OBJECT-TYPE
   SYNTAX      DisplayString
   MAX-ACCESS  read-only
   STATUS      current
   DESCRIPTION
       " "
   ::= { gel2esw10gSFPInfoEntry 4 }

gel2esw10gSFPTxCentralWavelength OBJECT-TYPE
   SYNTAX      DisplayString
   MAX-ACCESS  read-only
   STATUS      current
   DESCRIPTION
       " "
   ::= { gel2esw10gSFPInfoEntry 5 }

gel2esw10gSFPBaudRate OBJECT-TYPE
   SYNTAX      DisplayString
   MAX-ACCESS  read-only
   STATUS      current
   DESCRIPTION
       " "
   ::= { gel2esw10gSFPInfoEntry 6 }

gel2esw10gSFPVendorOUI OBJECT-TYPE
   SYNTAX      DisplayString
   MAX-ACCESS  read-only
   STATUS      current
   DESCRIPTION
       " "
   ::= { gel2esw10gSFPInfoEntry 7 }

gel2esw10gSFPVendorName OBJECT-TYPE
   SYNTAX      DisplayString
   MAX-ACCESS  read-only
   STATUS      current
   DESCRIPTION
       " "
   ::= { gel2esw10gSFPInfoEntry 8 }

gel2esw10gSFPVendorPN OBJECT-TYPE
   SYNTAX      DisplayString
   MAX-ACCESS  read-only
   STATUS      current
   DESCRIPTION
       " "
   ::= { gel2esw10gSFPInfoEntry 9 }

gel2esw10gSFPVendorRev OBJECT-TYPE
   SYNTAX      DisplayString
   MAX-ACCESS  read-only
   STATUS      current
   DESCRIPTION
       " "
   ::= { gel2esw10gSFPInfoEntry 10 }

gel2esw10gSFPVendorSN OBJECT-TYPE
   SYNTAX      DisplayString
   MAX-ACCESS  read-only
   STATUS      current
   DESCRIPTION
       " "
   ::= { gel2esw10gSFPInfoEntry 11 }

gel2esw10gSFPDateCode OBJECT-TYPE
   SYNTAX      DisplayString
   MAX-ACCESS  read-only
   STATUS      current
   DESCRIPTION
       " "
   ::= { gel2esw10gSFPInfoEntry 12 }

gel2esw10gSFPTemperature OBJECT-TYPE
   SYNTAX      DisplayString
   MAX-ACCESS  read-only
   STATUS      current
   DESCRIPTION
       " "
   ::= { gel2esw10gSFPInfoEntry 13 }

gel2esw10gSFPVcc OBJECT-TYPE
   SYNTAX      DisplayString
   MAX-ACCESS  read-only
   STATUS      current
   DESCRIPTION
       " "
   ::= { gel2esw10gSFPInfoEntry 14 }
   
gel2esw10gSFPMon1Bias OBJECT-TYPE
   SYNTAX      DisplayString
   MAX-ACCESS  read-only
   STATUS      current
   DESCRIPTION
       " "
   ::= { gel2esw10gSFPInfoEntry 15 }
   
gel2esw10gSFPMon2TxPWR OBJECT-TYPE
   SYNTAX      DisplayString
   MAX-ACCESS  read-only
   STATUS      current
   DESCRIPTION
       " "
   ::= { gel2esw10gSFPInfoEntry 16 }

gel2esw10gSFPMon3RxPWR OBJECT-TYPE
   SYNTAX      DisplayString
   MAX-ACCESS  read-only
   STATUS      current
   DESCRIPTION
       " "
   ::= { gel2esw10gSFPInfoEntry 17 }


gel2esw10gPortEEETable OBJECT-TYPE
   SYNTAX      SEQUENCE OF GEL2ESW10GPortEEEEntry
   MAX-ACCESS  not-accessible
   STATUS      current
   DESCRIPTION
      " "
   ::= { gel2esw10gPort 5 }

gel2esw10gPortEEEEntry OBJECT-TYPE
   SYNTAX      GEL2ESW10GPortEEEEntry
   MAX-ACCESS  not-accessible
   STATUS      current
   DESCRIPTION
       ""
   INDEX    { gel2esw10gPortEEEPort }
   ::= { gel2esw10gPortEEETable 1 }

GEL2ESW10GPortEEEEntry ::= SEQUENCE {
   gel2esw10gPortEEEPort		        INTEGER,
   gel2esw10gPortEEEMode		        INTEGER,
   gel2esw10gPortEEEUrgentQueue1		INTEGER,
   gel2esw10gPortEEEUrgentQueue2		INTEGER,
   gel2esw10gPortEEEUrgentQueue3		INTEGER,
   gel2esw10gPortEEEUrgentQueue4		INTEGER,
   gel2esw10gPortEEEUrgentQueue5		INTEGER,
   gel2esw10gPortEEEUrgentQueue6		INTEGER,
   gel2esw10gPortEEEUrgentQueue7		INTEGER,
   gel2esw10gPortEEEUrgentQueue8		INTEGER
}

gel2esw10gPortEEEPort OBJECT-TYPE
   SYNTAX      INTEGER (1..4095)
   MAX-ACCESS  not-accessible
   STATUS      current
   DESCRIPTION
       " "
   ::= { gel2esw10gPortEEEEntry 1 }

gel2esw10gPortEEEMode OBJECT-TYPE
   SYNTAX      INTEGER(0|1)
   MAX-ACCESS  read-write
   STATUS      current
   DESCRIPTION
       "default: 0
       0:disable
       1:enable "
   ::= { gel2esw10gPortEEEEntry 2 }

gel2esw10gPortEEEUrgentQueue1 OBJECT-TYPE
   SYNTAX      INTEGER(0|1)
   MAX-ACCESS  read-write
   STATUS      current
   DESCRIPTION
       "default: 0
       0:disable
       1:enable "
   ::= { gel2esw10gPortEEEEntry 3 }

gel2esw10gPortEEEUrgentQueue2 OBJECT-TYPE
   SYNTAX      INTEGER(0|1)
   MAX-ACCESS  read-write
   STATUS      current
   DESCRIPTION
       "default: 0
       0:disable
       1:enable "
   ::= { gel2esw10gPortEEEEntry 4 }

gel2esw10gPortEEEUrgentQueue3 OBJECT-TYPE
   SYNTAX      INTEGER(0|1)
   MAX-ACCESS  read-write
   STATUS      current
   DESCRIPTION
       "default: 0
       0:disable
       1:enable "
   ::= { gel2esw10gPortEEEEntry 5 }

gel2esw10gPortEEEUrgentQueue4 OBJECT-TYPE
   SYNTAX      INTEGER(0|1)
   MAX-ACCESS  read-write
   STATUS      current
   DESCRIPTION
       "default: 0
       0:disable
       1:enable "
   ::= { gel2esw10gPortEEEEntry 6 }

gel2esw10gPortEEEUrgentQueue5 OBJECT-TYPE
   SYNTAX      INTEGER(0|1)
   MAX-ACCESS  read-write
   STATUS      current
   DESCRIPTION
       "default: 0
       0:disable
       1:enable "
   ::= { gel2esw10gPortEEEEntry 7 }

gel2esw10gPortEEEUrgentQueue6 OBJECT-TYPE
   SYNTAX      INTEGER(0|1)
   MAX-ACCESS  read-write
   STATUS      current
   DESCRIPTION
       "default: 0
       0:disable
       1:enable "
   ::= { gel2esw10gPortEEEEntry 8 }

gel2esw10gPortEEEUrgentQueue7 OBJECT-TYPE
   SYNTAX      INTEGER(0|1)
   MAX-ACCESS  read-write
   STATUS      current
   DESCRIPTION
       "default: 0
       0:disable
       1:enable "
   ::= { gel2esw10gPortEEEEntry 9 }

gel2esw10gPortEEEUrgentQueue8 OBJECT-TYPE
   SYNTAX      INTEGER(0|1)
   MAX-ACCESS  read-write
   STATUS      current
   DESCRIPTION
       "default: 0
       0:disable
       1:enable "
   ::= { gel2esw10gPortEEEEntry 10 }


gel2esw10gVoiceVLAN                                             OBJECT IDENTIFIER ::= { gel2esw10gConfiguration 2 }

gel2esw10gVoiceVLANConf                                         OBJECT IDENTIFIER ::= { gel2esw10gVoiceVLAN 1 }

gel2esw10gVoiceVLANMode OBJECT-TYPE
   SYNTAX      INTEGER (0|1)
   MAX-ACCESS  read-write
   STATUS      current
   DESCRIPTION
       " Voice VLAN mode operation.
       default: 0,
       0: disable
       1: enable"
   ::= { gel2esw10gVoiceVLANConf 1 }

gel2esw10gVoiceVLANVLANId OBJECT-TYPE
   SYNTAX      INTEGER (1..4094)
   MAX-ACCESS  read-write
   STATUS      current
   DESCRIPTION
       "Voice VLAN ID.
        default: 1000,
        range : 1-4094. "
   ::= { gel2esw10gVoiceVLANConf 2 }

gel2esw10gVoiceVLANAgingTime OBJECT-TYPE
   SYNTAX      INTEGER (10..1000000)
   MAX-ACCESS  read-write
   STATUS      current
   DESCRIPTION
       " Voice VLAN secure learning aging time. 
         default: 86400,
         range : 10 - 10000000. "
   ::= { gel2esw10gVoiceVLANConf 3 }

gel2esw10gVoiceVLANTrafficClass OBJECT-TYPE
   SYNTAX      INTEGER (0..7)
   MAX-ACCESS  read-write
   STATUS      current
   DESCRIPTION
       " Voice VLAN traffic class, all traffic on the Voice VLAN
         will apply this class, available value is from 0(Low)
         to 7(High).
         default: 7. "
   ::= { gel2esw10gVoiceVLANConf 4 }


gel2esw10gVoiceVLANPortTable OBJECT-TYPE
   SYNTAX      SEQUENCE OF GEL2ESW10GVoiceVLANPortEntry
   MAX-ACCESS  not-accessible
   STATUS      current
   DESCRIPTION
       " Show Voice Vlan configuration. "
   ::= { gel2esw10gVoiceVLANConf 5 }

gel2esw10gVoiceVLANPortEntry OBJECT-TYPE
   SYNTAX      GEL2ESW10GVoiceVLANPortEntry
   MAX-ACCESS  not-accessible
   STATUS      current
   DESCRIPTION
       ""
   INDEX    { gel2esw10gVoiceVLANPort  }
   ::= { gel2esw10gVoiceVLANPortTable 1 }

GEL2ESW10GVoiceVLANPortEntry ::= SEQUENCE {
   gel2esw10gVoiceVLANPort                    INTEGER,
   gel2esw10gVoiceVLANPortMode                INTEGER,
   gel2esw10gVoiceVLANPortSecurity            INTEGER,
   gel2esw10gVoiceVLANPortDiscoveryProtocol   INTEGER
}

gel2esw10gVoiceVLANPort OBJECT-TYPE
   SYNTAX      INTEGER (1..4095)
   MAX-ACCESS  not-accessible
   STATUS      current
   DESCRIPTION
       " port, range : 1 - port number. "
   ::= { gel2esw10gVoiceVLANPortEntry 1 }

gel2esw10gVoiceVLANPortMode OBJECT-TYPE
   SYNTAX      INTEGER (0..2)
   MAX-ACCESS  read-write
   STATUS      current
   DESCRIPTION
       " Voice VLAN port mode.  
         default: 0,
         0: Disable (Disjoin from Voice VLAN.)
         1: Auto (Enable auto detect mode. It detects whether there is VoIP phone attached to the specific port and configures the Voice VLAN members automatically.)
         2: Forced (Force join to Voice VLAN.)"
   ::= { gel2esw10gVoiceVLANPortEntry 2 }

gel2esw10gVoiceVLANPortSecurity OBJECT-TYPE
   SYNTAX      INTEGER (0|1)
   MAX-ACCESS  read-write
   STATUS      current
   DESCRIPTION
       " Voice VLAN port security mode. 
         default: 0,
         0: Disable (Disjoin from Voice VLAN.)
         1: enable ( Enable Voice VLAN security mode. When the function is
                     enabled, all non-telephone MAC address in Voice VLAN
                     will be blocked 10 seconds.)"
   ::= { gel2esw10gVoiceVLANPortEntry 3 }

gel2esw10gVoiceVLANPortDiscoveryProtocol OBJECT-TYPE
   SYNTAX      INTEGER (0..2)
   MAX-ACCESS  read-write
   STATUS      current
   DESCRIPTION
       " Voice VLAN port discovery protocol.  
         default: 0
         0: OUI (Detect telephony device by OUI address.)
         1: LLDP (Detect telephony device by LLDP.)
         2: Both (Both OUI and LLDP.) "
   ::= { gel2esw10gVoiceVLANPortEntry 4 }


gel2esw10gVoiceVLANOUI                                          OBJECT IDENTIFIER ::= { gel2esw10gVoiceVLAN 2 }

gel2esw10gVoiceVLANOUICreate OBJECT-TYPE
   SYNTAX       INTEGER(0|1)
   MAX-ACCESS   read-write
   STATUS       current
   DESCRIPTION
       "default: 0
        0 : None  (read only)
        1 : Create an OUI entry"
   ::= { gel2esw10gVoiceVLANOUI 1 }

gel2esw10gVoiceVLANOUITable OBJECT-TYPE
   SYNTAX      SEQUENCE OF GEL2ESW10GVoiceVLANOUIEntry
   MAX-ACCESS  not-accessible
   STATUS      current
   DESCRIPTION
       " Create Voice VLAN OUI entry. Modify OUI table will
         restart auto detect OUI process. "
   ::= { gel2esw10gVoiceVLANOUI 2 }

gel2esw10gVoiceVLANOUIEntry OBJECT-TYPE
   SYNTAX      GEL2ESW10GVoiceVLANOUIEntry
   MAX-ACCESS  not-accessible
   STATUS      current
   DESCRIPTION
       ""
   INDEX    { gel2esw10gVoiceVLANOUIIndex  }
   ::= { gel2esw10gVoiceVLANOUITable 1 }

GEL2ESW10GVoiceVLANOUIEntry ::= SEQUENCE {
   gel2esw10gVoiceVLANOUIIndex         INTEGER,
   gel2esw10gVoiceVLANTelephonyOUI     OCTET STRING,
   gel2esw10gVoiceVLANDescription      DisplayString,
   gel2esw10gVoiceVLANOUIRowStatus     INTEGER
}

gel2esw10gVoiceVLANOUIIndex OBJECT-TYPE
   SYNTAX      INTEGER (1..16)
   MAX-ACCESS  not-accessible
   STATUS      current
   DESCRIPTION
       " "
   ::= { gel2esw10gVoiceVLANOUIEntry 1 }

gel2esw10gVoiceVLANTelephonyOUI OBJECT-TYPE
   SYNTAX      OCTET STRING (SIZE (1..32))
   MAX-ACCESS  read-write
   STATUS      current
   DESCRIPTION
       "OUI address, format : 0a 1b 2c "
   ::= { gel2esw10gVoiceVLANOUIEntry 2 }

gel2esw10gVoiceVLANDescription OBJECT-TYPE
   SYNTAX      DisplayString (SIZE (1..32))
   MAX-ACCESS  read-write
   STATUS      current
   DESCRIPTION
       " Up to 32 characters describing OUI address. "
   ::= { gel2esw10gVoiceVLANOUIEntry 3 }

gel2esw10gVoiceVLANOUIRowStatus OBJECT-TYPE
   SYNTAX      INTEGER (1..5)
   MAX-ACCESS  read-write
   STATUS      current
   DESCRIPTION
       "1: active
        2: notInservice
        4: destroy
        5: undo"
   ::= { gel2esw10gVoiceVLANOUIEntry 4 }

gel2esw10gGARP                                                   OBJECT IDENTIFIER ::= { gel2esw10gConfiguration 3 }

gel2esw10gGARPConfTable OBJECT-TYPE
   SYNTAX      SEQUENCE OF GEL2ESW10GGARPConfEntry
   MAX-ACCESS  not-accessible
   STATUS      current
   DESCRIPTION
       " "
   ::= { gel2esw10gGARP 1 }

gel2esw10gGARPConfEntry OBJECT-TYPE
   SYNTAX      GEL2ESW10GGARPConfEntry
   MAX-ACCESS  not-accessible
   STATUS      current
   DESCRIPTION
       ""
   INDEX    { gel2esw10gGARPConfPort  }
   ::= { gel2esw10gGARPConfTable 1 }

GEL2ESW10GGARPConfEntry ::= SEQUENCE {
   gel2esw10gGARPConfPort           INTEGER,
   gel2esw10gGARPJoinTimer          INTEGER,
   gel2esw10gGARPLeaveTimer         INTEGER,
   gel2esw10gGARPLeaveAllTimer      INTEGER,
   gel2esw10gGARPApplicantion       INTEGER,
   gel2esw10gGARPAttributeType      INTEGER,
   gel2esw10gGARPApplicant          INTEGER
}

gel2esw10gGARPConfPort OBJECT-TYPE
   SYNTAX      INTEGER (1..4095)
   MAX-ACCESS  not-accessible
   STATUS      current
   DESCRIPTION
       " "
   ::= { gel2esw10gGARPConfEntry 1 }

gel2esw10gGARPJoinTimer OBJECT-TYPE
   SYNTAX      INTEGER (200..1000)
   MAX-ACCESS  read-write
   STATUS      current
   DESCRIPTION
       "default: 200, range : 200 - 1000 "
   ::= { gel2esw10gGARPConfEntry 2 }

gel2esw10gGARPLeaveTimer OBJECT-TYPE
   SYNTAX      INTEGER (600..3000)
   MAX-ACCESS  read-write
   STATUS      current
   DESCRIPTION
       "default: 600 , range : 600 - 3000"
   ::= { gel2esw10gGARPConfEntry 3 }

gel2esw10gGARPLeaveAllTimer OBJECT-TYPE
   SYNTAX      INTEGER (10000..50000)
   MAX-ACCESS  read-write
   STATUS      current
   DESCRIPTION
       "default: 10000, range : 10000 - 50000 "
   ::= { gel2esw10gGARPConfEntry 4 }

gel2esw10gGARPApplicantion OBJECT-TYPE
   SYNTAX      INTEGER(1)
   MAX-ACCESS  read-write
   STATUS      current
   DESCRIPTION
       "default: 1
       1: GVRP"
   ::= { gel2esw10gGARPConfEntry 5 }

gel2esw10gGARPAttributeType OBJECT-TYPE
   SYNTAX      INTEGER(1)
   MAX-ACCESS  read-write
   STATUS      current
   DESCRIPTION
       "default: 1
       1: VLAN"
   ::= { gel2esw10gGARPConfEntry 6 }

gel2esw10gGARPApplicant OBJECT-TYPE
   SYNTAX      INTEGER(0|1)
   MAX-ACCESS  read-write
   STATUS      current
   DESCRIPTION
       "default: 0
       0: normal-participant
       1: non-participant"
   ::= { gel2esw10gGARPConfEntry 7 }

gel2esw10gGARPStatisticsTable OBJECT-TYPE
   SYNTAX      SEQUENCE OF GEL2ESW10GGARPStatisticsEntry
   MAX-ACCESS  not-accessible
   STATUS      current
   DESCRIPTION
       " Show the basic GARP port statistics. "
   ::= { gel2esw10gGARP 2 }

gel2esw10gGARPStatisticsEntry OBJECT-TYPE
   SYNTAX      GEL2ESW10GGARPStatisticsEntry
   MAX-ACCESS  not-accessible
   STATUS      current
   DESCRIPTION
       ""
   INDEX    { gel2esw10gGARPStatisticsPort  }
   ::= { gel2esw10gGARPStatisticsTable 1 }

GEL2ESW10GGARPStatisticsEntry ::= SEQUENCE {
   gel2esw10gGARPStatisticsPort             INTEGER,
   gel2esw10gGARPStatisticsPeerMAC          DisplayString,
   gel2esw10gGARPStatisticsFailedCount      Counter32
}

gel2esw10gGARPStatisticsPort OBJECT-TYPE
   SYNTAX      INTEGER (1..4095)
   MAX-ACCESS  not-accessible
   STATUS      current
   DESCRIPTION
       " port, range : 1 - port number. "
   ::= { gel2esw10gGARPStatisticsEntry 1 }

gel2esw10gGARPStatisticsPeerMAC OBJECT-TYPE
   SYNTAX      DisplayString
   MAX-ACCESS  read-only
   STATUS      current
   DESCRIPTION
       " Peer MAC is MAC address of the neighbour Switch from with GARP frame is received.  "
   ::= { gel2esw10gGARPStatisticsEntry 2 }

gel2esw10gGARPStatisticsFailedCount OBJECT-TYPE
   SYNTAX      Counter32
   MAX-ACCESS  read-only
   STATUS      current
   DESCRIPTION
       " explain Failed count here. "
   ::= { gel2esw10gGARPStatisticsEntry 3 }

gel2esw10gGVRP                                                   OBJECT IDENTIFIER ::= { gel2esw10gConfiguration 4 }

gel2esw10gGVRPConf                                                   OBJECT IDENTIFIER ::= { gel2esw10gGVRP 1 }

gel2esw10gGVRPMode OBJECT-TYPE
   SYNTAX      INTEGER(0|1)
   MAX-ACCESS  read-write
   STATUS      current
   DESCRIPTION
       "default: 0,
        0: disable, 
        1: enable. "
   ::= { gel2esw10gGVRPConf 1 }

gel2esw10gGVRPConfTable OBJECT-TYPE
   SYNTAX      SEQUENCE OF GEL2ESW10GGVRPConfEntry
   MAX-ACCESS  not-accessible
   STATUS      current
   DESCRIPTION
       " "
   ::= { gel2esw10gGVRPConf 2 }

gel2esw10gGVRPConfEntry OBJECT-TYPE
   SYNTAX      GEL2ESW10GGVRPConfEntry
   MAX-ACCESS  not-accessible
   STATUS      current
   DESCRIPTION
       ""
   INDEX    { gel2esw10gGVRPConfPort  }
   ::= { gel2esw10gGVRPConfTable 1 }

GEL2ESW10GGVRPConfEntry ::= SEQUENCE {
   gel2esw10gGVRPConfPort           INTEGER,
   gel2esw10gGVRPConfPortMode       INTEGER,
   gel2esw10gGVRPConfPortRRole      INTEGER
}

gel2esw10gGVRPConfPort OBJECT-TYPE
   SYNTAX      INTEGER (1..4095)
   MAX-ACCESS  not-accessible
   STATUS      current
   DESCRIPTION
       " "
   ::= { gel2esw10gGVRPConfEntry 1 }

gel2esw10gGVRPConfPortMode OBJECT-TYPE
   SYNTAX      INTEGER(0|1)
   MAX-ACCESS  read-write
   STATUS      current
   DESCRIPTION
       "default: 0
       1: enable
       0: disable"
   ::= { gel2esw10gGVRPConfEntry 2 }

gel2esw10gGVRPConfPortRRole OBJECT-TYPE
   SYNTAX      INTEGER(0|1)
   MAX-ACCESS  read-write
   STATUS      current
   DESCRIPTION
       "default: 0
       1: enable
       0: disable"
   ::= { gel2esw10gGVRPConfEntry 3 }

gel2esw10gGVRPStatisticsTable OBJECT-TYPE
   SYNTAX      SEQUENCE OF GEL2ESW10GGVRPStatisticsEntry
   MAX-ACCESS  not-accessible
   STATUS      current
   DESCRIPTION
       " "
   ::= { gel2esw10gGVRP 2 }

gel2esw10gGVRPStatisticsEntry OBJECT-TYPE
   SYNTAX      GEL2ESW10GGVRPStatisticsEntry
   MAX-ACCESS  not-accessible
   STATUS      current
   DESCRIPTION
       ""
   INDEX    { gel2esw10gGVRPStatisticsPort  }
   ::= { gel2esw10gGVRPStatisticsTable 1 }

GEL2ESW10GGVRPStatisticsEntry ::= SEQUENCE {
   gel2esw10gGVRPStatisticsPort         INTEGER,
   gel2esw10gGVRPStatisticsJoinTxCnt    Counter32,
   gel2esw10gGVRPStatisticsLeaveTxCnt   Counter32
}

gel2esw10gGVRPStatisticsPort OBJECT-TYPE
   SYNTAX      INTEGER (1..4095)
   MAX-ACCESS  not-accessible
   STATUS      current
   DESCRIPTION
       " "
   ::= { gel2esw10gGVRPStatisticsEntry 1 }

gel2esw10gGVRPStatisticsJoinTxCnt OBJECT-TYPE
   SYNTAX      Counter32
   MAX-ACCESS  read-only
   STATUS      current
   DESCRIPTION
       ""
   ::= { gel2esw10gGVRPStatisticsEntry 2 }

gel2esw10gGVRPStatisticsLeaveTxCnt OBJECT-TYPE
   SYNTAX      Counter32
   MAX-ACCESS  read-only
   STATUS      current
   DESCRIPTION
       ""
   ::= { gel2esw10gGVRPStatisticsEntry 3 }

gel2esw10gThermalProtection                                     OBJECT IDENTIFIER ::= { gel2esw10gConfiguration 5 }

gel2esw10gPriority0Temperature OBJECT-TYPE
   SYNTAX      INTEGER(0..255)
   MAX-ACCESS  read-write
   STATUS      current
   DESCRIPTION
       "default: 255, range : 0 - 255 "
   ::= { gel2esw10gThermalProtection 1 }

gel2esw10gPriority1Temperature OBJECT-TYPE
   SYNTAX      INTEGER(0..255)
   MAX-ACCESS  read-write
   STATUS      current
   DESCRIPTION
       "default: 255, range : 0 - 255 "
   ::= { gel2esw10gThermalProtection 2 }

gel2esw10gPriority2Temperature OBJECT-TYPE
   SYNTAX      INTEGER(0..255)
   MAX-ACCESS  read-write
   STATUS      current
   DESCRIPTION
       "default: 255, range : 0 - 255 "
   ::= { gel2esw10gThermalProtection 3 }

gel2esw10gPriority3Temperature OBJECT-TYPE
   SYNTAX      INTEGER(0..255)
   MAX-ACCESS  read-write
   STATUS      current
   DESCRIPTION
       "default: 255, range : 0 - 255 "
   ::= { gel2esw10gThermalProtection 4 }

gel2esw10gThermalProtectionTable OBJECT-TYPE
   SYNTAX      SEQUENCE OF GEL2ESW10GThermalProtectionEntry
   MAX-ACCESS  not-accessible
   STATUS      current
   DESCRIPTION
       " "
   ::= { gel2esw10gThermalProtection 5 }

gel2esw10gThermalProtectionEntry OBJECT-TYPE
   SYNTAX      GEL2ESW10GThermalProtectionEntry
   MAX-ACCESS  not-accessible
   STATUS      current
   DESCRIPTION
       ""
   INDEX    { gel2esw10gThermalProtectionPort  }
   ::= { gel2esw10gThermalProtectionTable 1 }

GEL2ESW10GThermalProtectionEntry ::= SEQUENCE {
   gel2esw10gThermalProtectionPort              INTEGER,
   gel2esw10gThermalProtectionPortTemperature   INTEGER,
   gel2esw10gThermalProtectionPortPriority      INTEGER,
   gel2esw10gThermalProtectionPortStatus        DisplayString
}

gel2esw10gThermalProtectionPort OBJECT-TYPE
   SYNTAX      INTEGER (1..4095)
   MAX-ACCESS  not-accessible
   STATUS      current
   DESCRIPTION
       " "
   ::= { gel2esw10gThermalProtectionEntry 1 }
   
gel2esw10gThermalProtectionPortTemperature OBJECT-TYPE
   SYNTAX      INTEGER(0..255)
   MAX-ACCESS  read-only
   STATUS      current
   DESCRIPTION
       ""
   ::= { gel2esw10gThermalProtectionEntry 2 }
   
gel2esw10gThermalProtectionPortPriority OBJECT-TYPE
   SYNTAX      INTEGER(0..3)
   MAX-ACCESS  read-write
   STATUS      current
   DESCRIPTION
       "default: 0, range : 0 - 3"
   ::= { gel2esw10gThermalProtectionEntry 3 }

gel2esw10gThermalProtectionPortStatus OBJECT-TYPE
   SYNTAX      DisplayString
   MAX-ACCESS  read-only
   STATUS      current
   DESCRIPTION
       ""
   ::= { gel2esw10gThermalProtectionEntry 4 }


gel2esw10gMirroring                                             OBJECT IDENTIFIER ::= { gel2esw10gConfiguration 6 }

gel2esw10gPortToMirrorOn OBJECT-TYPE
   SYNTAX      INTEGER(0..10)
   MAX-ACCESS  read-write
   STATUS      current
   DESCRIPTION
       "default: 0 
        0: disable,
        range : 1 - port number. "
   ::= { gel2esw10gMirroring 1 }

gel2esw10gMirrorTable OBJECT-TYPE
   SYNTAX      SEQUENCE OF GEL2ESW10GMirrorEntry
   MAX-ACCESS  not-accessible
   STATUS      current
   DESCRIPTION
       " "
   ::= { gel2esw10gMirroring 2 }

gel2esw10gMirrorEntry OBJECT-TYPE
   SYNTAX      GEL2ESW10GMirrorEntry
   MAX-ACCESS  not-accessible
   STATUS      current
   DESCRIPTION
       ""
   INDEX    { gel2esw10gMirrorPort  }
   ::= { gel2esw10gMirrorTable 1 }

GEL2ESW10GMirrorEntry ::= SEQUENCE {
   gel2esw10gMirrorPort		INTEGER,
   gel2esw10gMirrorMode		INTEGER
}

gel2esw10gMirrorPort OBJECT-TYPE
   SYNTAX      INTEGER (1..4095)
   MAX-ACCESS  not-accessible
   STATUS      current
   DESCRIPTION
       " "
   ::= { gel2esw10gMirrorEntry 1 }

gel2esw10gMirrorMode OBJECT-TYPE
   SYNTAX      INTEGER(0..3)
   MAX-ACCESS  read-write
   STATUS      current
   DESCRIPTION
       "default: 0
       0: disable
       1: enable
       2: rx only
       3: tx only
       Setting Tx mirroring for analyzer port has no effect. Tx mirroring ignored"
   ::= { gel2esw10gMirrorEntry 2 }

gel2esw10gTrapEventSeverity                                             OBJECT IDENTIFIER ::= { gel2esw10gConfiguration 7 }

gel2esw10gTrapEventSeverityACL OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 1 }

gel2esw10gTrapEventSeverityACLLog OBJECT-TYPE
   SYNTAX      INTEGER (0..7)
   MAX-ACCESS  read-write
   STATUS      current
   DESCRIPTION
       " default:  7(Debug)
        0: Emergency
        1: Alert
        2: Critical
        3: Error
        4: Warning
        5: Notice
        6: Info
        7: Debug"
   ::= { gel2esw10gTrapEventSeverity 2 }

gel2esw10gTrapEventSeverityAccessMgmt OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 3 }

gel2esw10gTrapEventSeverityAuthFailed OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw10gTrapEventSeverity 4 }

gel2esw10gTrapEventSeverityColdStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw10gTrapEventSeverity 5 }

gel2esw10gTrapEventSeverityConfigInfo OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 6 }

gel2esw10gTrapEventSeverityFirmwareUpgrade OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 7 }

gel2esw10gTrapEventSeverityImportExport OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 8 }

gel2esw10gTrapEventSeverityLACP OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 9 }

gel2esw10gTrapEventSeverityLinkStatus OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw10gTrapEventSeverity 10 }

gel2esw10gTrapEventSeverityLogin OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 11 }

gel2esw10gTrapEventSeverityLogout OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 12 }

gel2esw10gTrapEventSeverityLoopProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 13 }

gel2esw10gTrapEventSeverityMgmtIPChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 14 }

gel2esw10gTrapEventSeverityModuleChange OBJECT-TYPE
   SYNTAX      INTEGER (0..7)
   MAX-ACCESS  read-write
   STATUS      current
   DESCRIPTION
       " default:  5(Notice)
        0: Emergency
        1: Alert
        2: Critical
        3: Error
        4: Warning
        5: Notice
        6: Info
        7: Debug"
   ::= { gel2esw10gTrapEventSeverity 15 }

gel2esw10gTrapEventSeverityNAS OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 16 }

gel2esw10gTrapEventSeverityPasswdChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 17 }

gel2esw10gTrapEventSeverityPortSecurity OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 18 }

gel2esw10gTrapEventSeverityThermalProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 19 }

gel2esw10gTrapEventSeverityVLAN OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gel2esw10gTrapEventSeverity 20 }

gel2esw10gTrapEventSeverityWarmStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gel2esw10gTrapEventSeverity 21 }


gel2esw10gSMTP                                             OBJECT IDENTIFIER ::= { gel2esw10gConfiguration 8 }

gel2esw10gSMTPMailServer OBJECT-TYPE
   SYNTAX      DisplayString
   MAX-ACCESS  read-write
   STATUS      current
   DESCRIPTION
       " Up to 47 characters describing email server. "
   ::= { gel2esw10gSMTP 1 }

gel2esw10gSMTPUserName OBJECT-TYPE
   SYNTAX      DisplayString
   MAX-ACCESS  read-write
   STATUS      current
   DESCRIPTION
       " Up to 47 characters describing user name. "
   ::= { gel2esw10gSMTP 2 }

gel2esw10gSMTPPassword OBJECT-TYPE
   SYNTAX      DisplayString
   MAX-ACCESS  read-write
   STATUS      current
   DESCRIPTION
       " Up to 47 characters describing password. "
   ::= { gel2esw10gSMTP 3 }

gel2esw10gSMTPServeriryLevel OBJECT-TYPE
   SYNTAX      INTEGER(0..7)
   MAX-ACCESS  read-write
   STATUS      current
   DESCRIPTION
       "default: 6
       0: Emergency
       1: Alert
       2: Critical
       3: Error
       4: Warning
       5: Notice
       6: Info
       7: Debug"
   ::= { gel2esw10gSMTP 4 }

gel2esw10gSMTPSender OBJECT-TYPE
   SYNTAX      DisplayString
   MAX-ACCESS  read-write
   STATUS      current
   DESCRIPTION
       " Up to 47 characters describing sender. "
   ::= { gel2esw10gSMTP 5 }

gel2esw10gSMTPReturnPath OBJECT-TYPE
   SYNTAX      DisplayString
   MAX-ACCESS  read-write
   STATUS      current
   DESCRIPTION
       " Up to 47 characters describing return path. "
   ::= { gel2esw10gSMTP 6 }

gel2esw10gSMTPEmailAddress1 OBJECT-TYPE
   SYNTAX      DisplayString
   MAX-ACCESS  read-write
   STATUS      current
   DESCRIPTION
       " Up to 47 characters describing mail address. "
   ::= { gel2esw10gSMTP 7 }

gel2esw10gSMTPEmailAddress2 OBJECT-TYPE
   SYNTAX      DisplayString
   MAX-ACCESS  read-write
   STATUS      current
   DESCRIPTION
       " Up to 47 characters describing mail address. "
   ::= { gel2esw10gSMTP 8 }

gel2esw10gSMTPEmailAddress3 OBJECT-TYPE
   SYNTAX      DisplayString
   MAX-ACCESS  read-write
   STATUS      current
   DESCRIPTION
       " Up to 47 characters describing mail address. "
   ::= { gel2esw10gSMTP 9 }

gel2esw10gSMTPEmailAddress4 OBJECT-TYPE
   SYNTAX      DisplayString
   MAX-ACCESS  read-write
   STATUS      current
   DESCRIPTION
       " Up to 47 characters describing mail address. "
   ::= { gel2esw10gSMTP 10 }

gel2esw10gSMTPEmailAddress5 OBJECT-TYPE
   SYNTAX      DisplayString
   MAX-ACCESS  read-write
   STATUS      current
   DESCRIPTION
       " Up to 47 characters describing mail address. "
   ::= { gel2esw10gSMTP 11 }

gel2esw10gSMTPEmailAddress6 OBJECT-TYPE
   SYNTAX      DisplayString
   MAX-ACCESS  read-write
   STATUS      current
   DESCRIPTION
       " Up to 47 characters describing mail address. "
   ::= { gel2esw10gSMTP 12 }


gel2esw10gACL                                                   OBJECT IDENTIFIER ::= { gel2esw10gConfiguration 9 }

gel2esw10gACLPortsConfTable OBJECT-TYPE
   SYNTAX      SEQUENCE OF GEL2ESW10GACLPortsConfEntry
   MAX-ACCESS  not-accessible
   STATUS      current
   DESCRIPTION
       " "
   ::= { gel2esw10gACL 1 }

gel2esw10gACLPortsConfEntry OBJECT-TYPE
   SYNTAX      GEL2ESW10GACLPortsConfEntry
   MAX-ACCESS  not-accessible
   STATUS      current
   DESCRIPTION
       ""
   INDEX    { gel2esw10gACLPortsConfPort  }
   ::= { gel2esw10gACLPortsConfTable 1 }

GEL2ESW10GACLPortsConfEntry ::= SEQUENCE {
   gel2esw10gACLPortsConfPort               INTEGER,
   gel2esw10gACLPortsConfPolicyID           INTEGER,
   gel2esw10gACLPortsConfAction             INTEGER,
   gel2esw10gACLPortsConfRateLimiterID      INTEGER,
   gel2esw10gACLPortsConfPortRedirect       INTEGER,
   gel2esw10gACLPortsConfMirror             INTEGER,
   gel2esw10gACLPortsConfLogging            INTEGER,
   gel2esw10gACLPortsConfShutdown           INTEGER,
   gel2esw10gACLPortsConfState              INTEGER,
   gel2esw10gACLPortsConfCounter            Counter32
}

gel2esw10gACLPortsConfPort OBJECT-TYPE
   SYNTAX      INTEGER (1..4095)
   MAX-ACCESS  not-accessible
   STATUS      current
   DESCRIPTION
       " "
   ::= { gel2esw10gACLPortsConfEntry 1 }

gel2esw10gACLPortsConfPolicyID OBJECT-TYPE
   SYNTAX      INTEGER (0..255)
   MAX-ACCESS  read-write
   STATUS      current
   DESCRIPTION
       "default: 0, range : 0 - 255 "
   ::= { gel2esw10gACLPortsConfEntry 2 }

gel2esw10gACLPortsConfAction OBJECT-TYPE
   SYNTAX      INTEGER(0|1)
   MAX-ACCESS  read-write
   STATUS      current
   DESCRIPTION
       "default: 1,
        0: Deny
        1: Permit"
   ::= { gel2esw10gACLPortsConfEntry 3 }

gel2esw10gACLPortsConfRateLimiterID OBJECT-TYPE
   SYNTAX      INTEGER (0..16)
   MAX-ACCESS  read-write
   STATUS      current
   DESCRIPTION
       "default: 0,
        0: Disable
        range : 0 - 16 "
   ::= { gel2esw10gACLPortsConfEntry 4 }

gel2esw10gACLPortsConfPortRedirect OBJECT-TYPE
   SYNTAX      INTEGER (0..4095)
   MAX-ACCESS  read-write
   STATUS      current
   DESCRIPTION
       "default: 0
        0: Disable
        range : 0 - end port number "
   ::= { gel2esw10gACLPortsConfEntry 5 }

gel2esw10gACLPortsConfMirror OBJECT-TYPE
   SYNTAX      INTEGER(0|1)
   MAX-ACCESS  read-write
   STATUS      current
   DESCRIPTION
       "default: 0
        0: Disable
        1: Enable "
   ::= { gel2esw10gACLPortsConfEntry 6 }

gel2esw10gACLPortsConfLogging OBJECT-TYPE
   SYNTAX      INTEGER(0|1)
   MAX-ACCESS  read-write
   STATUS      current
   DESCRIPTION
       "default: 0
        0: Disable
        1: Enable "
   ::= { gel2esw10gACLPortsConfEntry 7 }

gel2esw10gACLPortsConfShutdown OBJECT-TYPE
   SYNTAX      INTEGER(0|1)
   MAX-ACCESS  read-write
   STATUS      current
   DESCRIPTION
       "default: 0
        0: Disable
        1: Enable "
   ::= { gel2esw10gACLPortsConfEntry 8 }
   
gel2esw10gACLPortsConfState OBJECT-TYPE
   SYNTAX      INTEGER(0|1)
   MAX-ACCESS  read-write
   STATUS      current
   DESCRIPTION
       "default: 1
        0: Disable
        1: Enable "
   ::= { gel2esw10gACLPortsConfEntry 9 }

gel2esw10gACLPortsConfCounter OBJECT-TYPE
   SYNTAX      Counter32
   MAX-ACCESS  read-only
   STATUS      current
   DESCRIPTION
       "Counts the number of frames that match this ACE. "
   ::= { gel2esw10gACLPortsConfEntry 10 }


gel2esw10gACLRateLimiterTable OBJECT-TYPE
   SYNTAX      SEQUENCE OF GEL2ESW10GACLRateLimiterEntry
   MAX-ACCESS  not-accessible
   STATUS      current
   DESCRIPTION
       " "
   ::= { gel2esw10gACL 2 }

gel2esw10gACLRateLimiterEntry OBJECT-TYPE
   SYNTAX      GEL2ESW10GACLRateLimiterEntry
   MAX-ACCESS  not-accessible
   STATUS      current
   DESCRIPTION
       ""
   INDEX    { gel2esw10gACLRateLimiterID  }
   ::= { gel2esw10gACLRateLimiterTable 1 }

GEL2ESW10GACLRateLimiterEntry ::= SEQUENCE {
   gel2esw10gACLRateLimiterID       INTEGER,
   gel2esw10gACLRateLimiterUnit     INTEGER,
   gel2esw10gACLRateLimiterRate     INTEGER
}

gel2esw10gACLRateLimiterID OBJECT-TYPE
   SYNTAX      INTEGER (1..16)
   MAX-ACCESS  not-accessible
   STATUS      current
   DESCRIPTION
       " Rate Limiter ID.
         range : 1-16 "
   ::= { gel2esw10gACLRateLimiterEntry 1 }

gel2esw10gACLRateLimiterUnit OBJECT-TYPE
   SYNTAX      INTEGER(0|1)
   MAX-ACCESS  read-write
   STATUS      current
   DESCRIPTION
       "default: 0, 
        0: pps
        1: kbps"
   ::= { gel2esw10gACLRateLimiterEntry 2 }

gel2esw10gACLRateLimiterRate OBJECT-TYPE
   SYNTAX      INTEGER (0..3276700)
   MAX-ACCESS  read-write
   STATUS      current
   DESCRIPTION
       "default: 1, 
        range : <0-3276700> pps
                <0-10000> kbps"
   ::= { gel2esw10gACLRateLimiterEntry 3 }


gel2esw10gACLACE                                          OBJECT IDENTIFIER ::= { gel2esw10gACL 3 }

gel2esw10gACLACECreate OBJECT-TYPE
   SYNTAX       INTEGER(0|1)
   MAX-ACCESS   read-write
   STATUS       current
   DESCRIPTION
       "default: 0
        0 : None  (read only)
        1 : Create an ACE entry"
   ::= { gel2esw10gACLACE 1 }

gel2esw10gACLACETable OBJECT-TYPE
   SYNTAX      SEQUENCE OF GEL2ESW10GACLACEEntry
   MAX-ACCESS  not-accessible
   STATUS      current
   DESCRIPTION
       " Create ACL ACE entry. "
   ::= { gel2esw10gACLACE 2 }

gel2esw10gACLACEEntry OBJECT-TYPE
   SYNTAX      GEL2ESW10GACLACEEntry
   MAX-ACCESS  not-accessible
   STATUS      current
   DESCRIPTION
       ""
   INDEX    { gel2esw10gACLACEIndex  }
   ::= { gel2esw10gACLACETable 1 }

GEL2ESW10GACLACEEntry ::= SEQUENCE {
   gel2esw10gACLACEIndex                INTEGER,
   gel2esw10gACLACEID                   INTEGER,
   gel2esw10gACLACENextID               INTEGER,
   gel2esw10gACLACEIngressPort          DisplayString,
   gel2esw10gACLACEPortPolicyNumber     INTEGER,
   
   gel2esw10gACLACEPortPolicyBitmask    INTEGER,
   gel2esw10gACLACEFrameType            INTEGER,
   gel2esw10gACLACEAction               INTEGER,
   gel2esw10gACLACEDenyPortRedirect     DisplayString,
   gel2esw10gACLACELogging              INTEGER,
   
   gel2esw10gACLACEMirror               INTEGER,
   gel2esw10gACLACERateLimiter          INTEGER,
   gel2esw10gACLACEShutdown             INTEGER,
   gel2esw10gACLACEVLAN8021QTagged      INTEGER,
   gel2esw10gACLACEVLANTagPriority      INTEGER,
   
   gel2esw10gACLACEVLANVID              INTEGER,
   gel2esw10gACLACEEtherType            INTEGER,
   gel2esw10gACLACESMAC                 DisplayString,
   gel2esw10gACLACEDMACType             INTEGER,
   gel2esw10gACLACEDMAC                 DisplayString,
   
   gel2esw10gACLACEArpOpcode            INTEGER,
   gel2esw10gACLACEArpFlagsRequestReply INTEGER,
   gel2esw10gACLACEArpFlagsArpSmac      INTEGER,
   gel2esw10gACLACEArpFlagsRarpDmac     INTEGER,
   gel2esw10gACLACEArpFlagsLength       INTEGER,
   
   gel2esw10gACLACEArpFlagsIp           INTEGER,
   gel2esw10gACLACEArpFlagsEthernet     INTEGER,
   gel2esw10gACLACESIPType              INTEGER,
   gel2esw10gACLACESIPIPAddress         IpAddress,                      
   gel2esw10gACLACESIPNetworkPrefix     INTEGER,
   
   gel2esw10gACLACEDIPType              INTEGER,
   gel2esw10gACLACEDIPIPAddress         IpAddress,                      
   gel2esw10gACLACEDIPNetworkPrefix     INTEGER,
   
   gel2esw10gACLACEIPProtocol           INTEGER,
   gel2esw10gACLACEIPFlagsTTL           INTEGER,
   gel2esw10gACLACEIPFlagsOptions       INTEGER,
   gel2esw10gACLACEIPFlagsFragment      INTEGER,
   gel2esw10gACLACEICMPType             INTEGER,
   
   gel2esw10gACLACEICMPCode             INTEGER,
   gel2esw10gACLACESourcePortMin        INTEGER,
   gel2esw10gACLACESourcePortMax        INTEGER,
   gel2esw10gACLACEDestPortMin          INTEGER,
   gel2esw10gACLACEDestPortMax          INTEGER,
   
   gel2esw10gACLACETCPFlagsFin          INTEGER,
   gel2esw10gACLACETCPFlagsSyn          INTEGER,
   gel2esw10gACLACETCPFlagsRst          INTEGER,
   gel2esw10gACLACETCPFlagsPsh          INTEGER,
   gel2esw10gACLACETCPFlagsAck          INTEGER,
   
   gel2esw10gACLACETCPFlagsUrg          INTEGER,
   
   gel2esw10gACLACERowStatus            INTEGER
}

gel2esw10gACLACEIndex OBJECT-TYPE
   SYNTAX      INTEGER (1..256)
   MAX-ACCESS  not-accessible
   STATUS      current
   DESCRIPTION
       " "
   ::= { gel2esw10gACLACEEntry 1 }

gel2esw10gACLACEID OBJECT-TYPE
   SYNTAX      INTEGER (1..256)
   MAX-ACCESS  read-write
   STATUS      current
   DESCRIPTION
       " If the ACE ID is specified and an entry with this ACE ID
         already exists, the ACE will be modified. Otherwise, a
         new ACE will be added.
         range : 1 - 256. "
   ::= { gel2esw10gACLACEEntry 2 }

gel2esw10gACLACENextID OBJECT-TYPE
   SYNTAX      INTEGER (0..256)
   MAX-ACCESS  read-write
   STATUS      current
   DESCRIPTION
       " If the next ACE ID is non zero, the ACE will be placed
         before this ACE in the list. If the next ACE ID is zero,
         the ACE will be placed last in the list.
         range : 0 - 256. "
   ::= { gel2esw10gACLACEEntry 3 }

gel2esw10gACLACEIngressPort OBJECT-TYPE
   SYNTAX      DisplayString
   MAX-ACCESS  read-write
   STATUS      current
   DESCRIPTION
       " Indicates the ingress port of the ACE. Possible values are: 
         All: The ACE will match all ingress port. 
         Port: The ACE will match a specific ingress port.Format: 1,3,6."
   ::= { gel2esw10gACLACEEntry 4 }

gel2esw10gACLACEPortPolicyNumber OBJECT-TYPE
   SYNTAX      INTEGER (0..255)
   MAX-ACCESS  read-write
   STATUS      current
   DESCRIPTION
       " policy value.
         range : 0 - 255. "
   ::= { gel2esw10gACLACEEntry 5 }
   
gel2esw10gACLACEPortPolicyBitmask OBJECT-TYPE
   SYNTAX      INTEGER (0..255)
   MAX-ACCESS  read-write
   STATUS      current
   DESCRIPTION
       " policy bitmask.
         range : 0 - 255(0xff). "
   ::= { gel2esw10gACLACEEntry 6 }

gel2esw10gACLACEFrameType OBJECT-TYPE
   SYNTAX      INTEGER (0..6)
   MAX-ACCESS  read-write
   STATUS      current
   DESCRIPTION
       " 0: any,
         1: arp,
         2: etype,
         3: icmp,
         4: ipv4,
         5: tcp,
         6: udp."
   ::= { gel2esw10gACLACEEntry 7 }

gel2esw10gACLACEAction OBJECT-TYPE
   SYNTAX      INTEGER(0|1)
   MAX-ACCESS  read-write
   STATUS      current
   DESCRIPTION
       "default: 1,
        0: Deny
        1: Permit"
   ::= { gel2esw10gACLACEEntry 8 }

gel2esw10gACLACEDenyPortRedirect OBJECT-TYPE
   SYNTAX      DisplayString
   MAX-ACCESS  read-write
   STATUS      current
   DESCRIPTION
       " Frames that hit the ACE are redirected to the port number specified here.  
         Disabled: indicates that the port redirect operation is disabled. 
         Port Format: 1,3,6."
   ::= { gel2esw10gACLACEEntry 9 }

gel2esw10gACLACELogging OBJECT-TYPE
   SYNTAX      INTEGER(0|1)
   MAX-ACCESS  read-write
   STATUS      current
   DESCRIPTION
       "default: 0,
        0: disable - Frames matching the ACE are not logged.
        1: enable - Frames matching the ACE are stored in the system log."
   ::= { gel2esw10gACLACEEntry 10 }

gel2esw10gACLACEMirror OBJECT-TYPE
   SYNTAX      INTEGER(0|1)
   MAX-ACCESS  read-write
   STATUS      current
   DESCRIPTION
       "default: 0,
        0: disable - Frames matching the ACE are not mirrored.
        1: enable - Frames matching the ACE are mirrored."
   ::= { gel2esw10gACLACEEntry 11 }

gel2esw10gACLACERateLimiter OBJECT-TYPE
   SYNTAX      INTEGER (0..16)
   MAX-ACCESS  read-write
   STATUS      current
   DESCRIPTION
       "default: 0,
        0: Disable
        range : 0 - 16 "
   ::= { gel2esw10gACLACEEntry 12 }

gel2esw10gACLACEShutdown OBJECT-TYPE
   SYNTAX      INTEGER(0|1)
   MAX-ACCESS  read-write
   STATUS      current
   DESCRIPTION
       "default: 0,
        0: disable - Port shut down is disabled for the AC.
        1: enable - If a frame matches the ACE, the ingress port will be disabled."
   ::= { gel2esw10gACLACEEntry 13 }

gel2esw10gACLACEVLAN8021QTagged OBJECT-TYPE
   SYNTAX      INTEGER (0..2)
   MAX-ACCESS  read-write
   STATUS      current
   DESCRIPTION
       "Specify whether frames can hit the action according to the 802.1Q tagged. 
        default: 2,
        0: disable - Untagged frame only.
        1: enable - Tagged frame only.
        2: Any - Any value is allowed. "
   ::= { gel2esw10gACLACEEntry 14 }

gel2esw10gACLACEVLANTagPriority OBJECT-TYPE
   SYNTAX      INTEGER (0..8)
   MAX-ACCESS  read-write
   STATUS      current
   DESCRIPTION
       "Specify the tag priority for this ACE.
        The tag priority can't be set when 802.1Q Tagged is disabled
        default: 8,
        8: Any,
        range : 0 - 8 "
   ::= { gel2esw10gACLACEEntry 15 }

gel2esw10gACLACEVLANVID OBJECT-TYPE
   SYNTAX      INTEGER (0..4094)
   MAX-ACCESS  read-write
   STATUS      current
   DESCRIPTION
       "Specify the VLAN ID filter for this ACE.
        The vid can't be set when 802.1Q Tagged is disabled. 
        default: 0,
        0: Any - No VLAN ID filter is specified.
        range : 0 - 4094 "
   ::= { gel2esw10gACLACEEntry 16 }

gel2esw10gACLACEEtherType OBJECT-TYPE
   SYNTAX      INTEGER (0..65535)
   MAX-ACCESS  read-write
   STATUS      current
   DESCRIPTION
       " 0: Any - Any but excluding 0x0800(IPv4) 0x0806(ARP) and 0x86DD(IPv6).
         range : 0 or 1536(0x0600)- 65535(0xffff). "
   ::= { gel2esw10gACLACEEntry 17 }

gel2esw10gACLACESMAC OBJECT-TYPE
   SYNTAX      DisplayString
   MAX-ACCESS  read-write
   STATUS      current
   DESCRIPTION
       " Configure source MAC address for this ACE.
         <mac-address>: A frame that hits this ACE matches this source MAC address value. 
         Any: Don't care."
   ::= { gel2esw10gACLACEEntry 18 }

gel2esw10gACLACEDMACType OBJECT-TYPE
   SYNTAX      INTEGER (0..4)
   MAX-ACCESS  read-write
   STATUS      current
   DESCRIPTION
       "DMAC Type.
        default: 0,
        0: Any - Don't care.
        1: Broadcast - Frame must be broadcast.
        2: Unicast - Frame must be unitcast.
        3: Multicast - Frame must be multicast.
        4: mac address
        range : 0 - 4 "
   ::= { gel2esw10gACLACEEntry 19 }

gel2esw10gACLACEDMAC OBJECT-TYPE
   SYNTAX      DisplayString
   MAX-ACCESS  read-write
   STATUS      current
   DESCRIPTION
       " Configure destination MAC address for this ACE. 
         <mac-address>: A frame that hits this ACE matches this destination MAC address value.            
         Any: Don't care.
         Broadcast: Frame must be broadcast.
         Unicast: Frame must be unitcast.
         Multicast: Frame must be multicast. "
   ::= { gel2esw10gACLACEEntry 20 }

gel2esw10gACLACEArpOpcode OBJECT-TYPE
   SYNTAX      INTEGER (0..3)
   MAX-ACCESS  read-write
   STATUS      current
   DESCRIPTION
       "Configure ARP opcode for this ACE.
        default: 0,
        0: Any - Don't care.
        1: arp.
        2: rarp.
        3: other.
        4: No data.
        range : 0 - 3 "
   ::= { gel2esw10gACLACEEntry 21 }

gel2esw10gACLACEArpFlagsRequestReply OBJECT-TYPE
   SYNTAX      INTEGER (0..2)
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 2 "
   ::= { gel2esw10gACLACEEntry 22 }

gel2esw10gACLACEArpFlagsArpSmac OBJECT-TYPE
   SYNTAX      INTEGER (0..2)
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 2 "
   ::= { gel2esw10gACLACEEntry 23 }   

gel2esw10gACLACEArpFlagsRarpDmac OBJECT-TYPE
   SYNTAX      INTEGER (0..2)
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 2 "
   ::= { gel2esw10gACLACEEntry 24 }

gel2esw10gACLACEArpFlagsLength OBJECT-TYPE
   SYNTAX      INTEGER (0..2)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 2 "
   ::= { gel2esw10gACLACEEntry 25 }

gel2esw10gACLACEArpFlagsIp OBJECT-TYPE
   SYNTAX      INTEGER (0..2)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 2 "
   ::= { gel2esw10gACLACEEntry 26 }

gel2esw10gACLACEArpFlagsEthernet OBJECT-TYPE
   SYNTAX      INTEGER (0..2)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 2 "
   ::= { gel2esw10gACLACEEntry 27 }
   
gel2esw10gACLACESIPType OBJECT-TYPE
   SYNTAX      INTEGER(0|1)
   MAX-ACCESS  read-write
   STATUS      current
   DESCRIPTION
       "Configure source IP address for this ACE.
        default: 0,
        0: Any - Don't care.
        1: IP Address.
        2: No data.
        range : 0 - 1"
   ::= { gel2esw10gACLACEEntry 28 }   
   
gel2esw10gACLACESIPIPAddress OBJECT-TYPE
   SYNTAX      IpAddress
   MAX-ACCESS  read-write
   STATUS      current
   DESCRIPTION
       "A frame that hits this ACE matches this source IP address value."
   ::= { gel2esw10gACLACEEntry 29 }      
   
gel2esw10gACLACESIPNetworkPrefix OBJECT-TYPE
   SYNTAX      INTEGER (1..32)
   MAX-ACCESS  read-write
   STATUS      current
   DESCRIPTION
       "Network prefix.
        default: 32,
        0: No data.
        range : 1 - 32"
   ::= { gel2esw10gACLACEEntry 30 }   
   

gel2esw10gACLACEDIPType OBJECT-TYPE
   SYNTAX      INTEGER(0|1)
   MAX-ACCESS  read-write
   STATUS      current
   DESCRIPTION
       "Configure destination IP address for this ACE.
        default: 0,
        0: Any - Don't care.
        1: IP Address.
        2: No data.
        range : 0 - 1"
   ::= { gel2esw10gACLACEEntry 32 }   
   
gel2esw10gACLACEDIPIPAddress OBJECT-TYPE
   SYNTAX      IpAddress
   MAX-ACCESS  read-write
   STATUS      current
   DESCRIPTION
       "A frame that hits this ACE matches this destination IP address value."
   ::= { gel2esw10gACLACEEntry 33 }      
   
gel2esw10gACLACEDIPNetworkPrefix OBJECT-TYPE
   SYNTAX      INTEGER (1..32)
   MAX-ACCESS  read-write
   STATUS      current
   DESCRIPTION
       "Network prefix.
        default: 32,
        0: No data.
        range : 1 - 32"
   ::= { gel2esw10gACLACEEntry 34 }  
   
   
gel2esw10gACLACEIPProtocol OBJECT-TYPE
   SYNTAX      INTEGER (0..256)
   MAX-ACCESS  read-write
   STATUS      current
   DESCRIPTION
       "Configure IP protocol for this ACE.
        default: 256,
        256: Any - Don't care.
        257: No data.
        range : 0 - 256"
   ::= { gel2esw10gACLACEEntry 36 } 

gel2esw10gACLACEIPFlagsTTL OBJECT-TYPE
   SYNTAX      INTEGER (0..2)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 2 "
   ::= { gel2esw10gACLACEEntry 37 }   
   
gel2esw10gACLACEIPFlagsOptions OBJECT-TYPE
   SYNTAX      INTEGER (0..2)
   MAX-ACCESS  read-write
   STATUS      current
   DESCRIPTION
       "Configure IP options flag for this ACE.
        default: 2,
        0: IPv4 frames where the options flag is unset.
        1: IPv4 frames where the options flag is set.
        2: Any - Don't care.
        3: No data.
        range : 0 - 2 "
   ::= { gel2esw10gACLACEEntry 38 }

gel2esw10gACLACEIPFlagsFragment OBJECT-TYPE
   SYNTAX      INTEGER (0..2)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 2 "
   ::= { gel2esw10gACLACEEntry 39 }

gel2esw10gACLACEICMPType OBJECT-TYPE
   SYNTAX      INTEGER (0..256)
   MAX-ACCESS  read-write
   STATUS      current
   DESCRIPTION
       "Configure ICMP type for this ACE.
        default: 256,
        256: Any - Don't care.
        257: No data.
        range : 0 - 256"
   ::= { gel2esw10gACLACEEntry 40 }   

gel2esw10gACLACEICMPCode OBJECT-TYPE
   SYNTAX      INTEGER (0..256)
   MAX-ACCESS  read-write
   STATUS      current
   DESCRIPTION
       "Configure ICMP code for this ACE.
        default: 256,
        256: Any - Don't care.
        257: No data.
        range : 0 - 256"
   ::= { gel2esw10gACLACEEntry 41 } 

gel2esw10gACLACESourcePortMin OBJECT-TYPE
   SYNTAX      INTEGER (0..65535)
   MAX-ACCESS  read-write
   STATUS      current
   DESCRIPTION
       "Configure Source UDP/TCP port range for this ACE.
        default: 0,
        65536: No data.
        range : 0 - 65535"
   ::= { gel2esw10gACLACEEntry 42 }     
   
gel2esw10gACLACESourcePortMax OBJECT-TYPE
   SYNTAX      INTEGER (0..65535)
   MAX-ACCESS  read-write
   STATUS      current
   DESCRIPTION
       "Configure Source UDP/TCP port range for this ACE.
        default: 0,
        65536: No data.
        range : 0 - 65535"
   ::= { gel2esw10gACLACEEntry 43 } 
      
gel2esw10gACLACEDestPortMin OBJECT-TYPE
   SYNTAX      INTEGER (0..65535)
   MAX-ACCESS  read-write
   STATUS      current
   DESCRIPTION
       "Configure Destination UDP/TCP port range for this ACE.
        default: 0,
        65536: No data.
        range : 0 - 65535"
   ::= { gel2esw10gACLACEEntry 44 }     

gel2esw10gACLACEDestPortMax OBJECT-TYPE
   SYNTAX      INTEGER (0..65535)
   MAX-ACCESS  read-write
   STATUS      current
   DESCRIPTION
       "Configure Destination UDP/TCP port range for this ACE.
        default: 0,
        65536: No data.
        range : 0 - 65535"
   ::= { gel2esw10gACLACEEntry 45 }

gel2esw10gACLACETCPFlagsFin OBJECT-TYPE
   SYNTAX      INTEGER (0..2)
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 2 "
   ::= { gel2esw10gACLACEEntry 46 }

gel2esw10gACLACETCPFlagsSyn OBJECT-TYPE
   SYNTAX      INTEGER (0..2)
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 2 "
   ::= { gel2esw10gACLACEEntry 47 }

gel2esw10gACLACETCPFlagsRst OBJECT-TYPE
   SYNTAX      INTEGER (0..2)
   MAX-ACCESS  read-write
   STATUS      current
   DESCRIPTION
       "Configure TCP (RST) flags for this ACE.
        default: 2,
        0: TCP frames where the RST field is unset.
        1: TCP frames where the RST field is set.
        2: Any - Don't care.
        3: No data.
        range : 0 - 2 "
   ::= { gel2esw10gACLACEEntry 48 }

gel2esw10gACLACETCPFlagsPsh OBJECT-TYPE
   SYNTAX      INTEGER (0..2)
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 2 "
   ::= { gel2esw10gACLACEEntry 49 }

gel2esw10gACLACETCPFlagsAck OBJECT-TYPE
   SYNTAX      INTEGER (0..2)
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 2 "
   ::= { gel2esw10gACLACEEntry 50 }

gel2esw10gACLACETCPFlagsUrg OBJECT-TYPE
   SYNTAX      INTEGER (0..2)
   MAX-ACCESS  read-write
   STATUS      current
   DESCRIPTION
       "Configure TCP (URG) flags for this ACE.
        default: 2,
        0: TCP frames where the URG field is unset.
        1: TCP frames where the URG field is set.
        2: Any - Don't care.
        3: No data.
        range : 0 - 2 "
   ::= { gel2esw10gACLACEEntry 51 }

gel2esw10gACLACERowStatus OBJECT-TYPE
   SYNTAX      INTEGER (1..5)
   MAX-ACCESS  read-write
   STATUS      current
   DESCRIPTION
       " 1: active
         2: notInservice
         4: destroy
         5: undo"
   ::= { gel2esw10gACLACEEntry 66 }


gel2esw10gACLACEClear OBJECT-TYPE
   SYNTAX       INTEGER(0|1)
   MAX-ACCESS   read-write
   STATUS       current
   DESCRIPTION
       "default: 0
        0 : No action
        1 : Clear all ACL counters."
   ::= { gel2esw10gACLACE 3 }

gel2esw10gACLACEMoveACEID OBJECT-TYPE
   SYNTAX       INTEGER (1..256)
   MAX-ACCESS   read-write
   STATUS       current
   DESCRIPTION
       "Move ACE,
        default: 0
        ACE ID must be exist.
        range : 1 - 256."
   ::= { gel2esw10gACLACE 4 }

gel2esw10gACLACEMoveNextACEID OBJECT-TYPE
   SYNTAX       INTEGER (0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gel2esw10gACLACE 5 }

gel2esw10gACLACEStatusTable OBJECT-TYPE
   SYNTAX      SEQUENCE OF GEL2ESW10GACLACEStatusEntry
   MAX-ACCESS  not-accessible
   STATUS      current
   DESCRIPTION
       " ACL ACE Status entry. "
   ::= { gel2esw10gACLACE 6 }

gel2esw10gACLACEStatusEntry OBJECT-TYPE
   SYNTAX      GEL2ESW10GACLACEStatusEntry
   MAX-ACCESS  not-accessible
   STATUS      current
   DESCRIPTION
       ""
   INDEX    { gel2esw10gACLACEStatusIndex  }
   ::= { gel2esw10gACLACEStatusTable 1 }

GEL2ESW10GACLACEStatusEntry ::= SEQUENCE {
   gel2esw10gACLACEStatusIndex          INTEGER,
   gel2esw10gACLACEStatusUser           DisplayString,
   gel2esw10gACLACEStatusID             INTEGER,
   gel2esw10gACLACEStatusIngressPort    DisplayString,
   gel2esw10gACLACEStatusFrameType      DisplayString,
   gel2esw10gACLACEStatusAction         DisplayString,
   gel2esw10gACLACEStatusRateLimiter    DisplayString,
   gel2esw10gACLACEStatusPortCopy       DisplayString,
   gel2esw10gACLACEStatusMirror         DisplayString,
   gel2esw10gACLACEStatusCPU            DisplayString,
   gel2esw10gACLACEStatusCounter        Counter32,
   gel2esw10gACLACEStatusConflict       DisplayString
}

gel2esw10gACLACEStatusIndex OBJECT-TYPE
   SYNTAX      INTEGER (1..256)
   MAX-ACCESS  not-accessible
   STATUS      current
   DESCRIPTION
       " "
   ::= { gel2esw10gACLACEStatusEntry 1 }

gel2esw10gACLACEStatusUser OBJECT-TYPE
   SYNTAX      DisplayString
   MAX-ACCESS  read-only
   STATUS      current
   DESCRIPTION
       " Indicates the ACL user. 
         S : Static.  
         IPMG : IP Management.  
         IPSG : IP Source Guard.  
         IPMC : IPMC.  
         ARPI : Arp Inspection.  
         UPnP : UPnP.  
         DHCP : DHCP. "
   ::= { gel2esw10gACLACEStatusEntry 2 }

gel2esw10gACLACEStatusID OBJECT-TYPE
   SYNTAX      INTEGER (1..256)
   MAX-ACCESS  read-only
   STATUS      current
   DESCRIPTION
       " ACE ID.
         range : 1 - 256. "
   ::= { gel2esw10gACLACEStatusEntry 3 }

gel2esw10gACLACEStatusIngressPort OBJECT-TYPE
   SYNTAX      DisplayString
   MAX-ACCESS  read-only
   STATUS      current
   DESCRIPTION
       " Indicates the ingress port of the ACE. Possible values are: 
         All: The ACE will match all ingress port. 
         Port: The ACE will match a specific ingress port. "
   ::= { gel2esw10gACLACEStatusEntry 4 }

gel2esw10gACLACEStatusFrameType OBJECT-TYPE
   SYNTAX      DisplayString
   MAX-ACCESS  read-only
   STATUS      current
   DESCRIPTION
       " Indicates the frame type of the ACE. "
   ::= { gel2esw10gACLACEStatusEntry 5 }

gel2esw10gACLACEStatusAction OBJECT-TYPE
   SYNTAX      DisplayString
   MAX-ACCESS  read-only
   STATUS      current
   DESCRIPTION
       " Indicates the forwarding action of the ACE. "
   ::= { gel2esw10gACLACEStatusEntry 6 }

gel2esw10gACLACEStatusRateLimiter OBJECT-TYPE
   SYNTAX      DisplayString
   MAX-ACCESS  read-only
   STATUS      current
   DESCRIPTION
       " Indicates the rate limiter number of the ACE. "
   ::= { gel2esw10gACLACEStatusEntry 7 }

gel2esw10gACLACEStatusPortCopy OBJECT-TYPE
   SYNTAX      DisplayString
   MAX-ACCESS  read-only
   STATUS      current
   DESCRIPTION
       " Indicates the port redirect operation of the ACE. Frames matching the ACE are redirected to the port number. "
   ::= { gel2esw10gACLACEStatusEntry 8 }

gel2esw10gACLACEStatusMirror OBJECT-TYPE
   SYNTAX      DisplayString
   MAX-ACCESS  read-only
   STATUS      current
   DESCRIPTION
       " Specify the mirror operation of this port. "
   ::= { gel2esw10gACLACEStatusEntry 9 }

gel2esw10gACLACEStatusCPU OBJECT-TYPE
   SYNTAX      DisplayString
   MAX-ACCESS  read-only
   STATUS      current
   DESCRIPTION
       " Forward packet that matched the specific ACE to CPU. "
   ::= { gel2esw10gACLACEStatusEntry 10 }

gel2esw10gACLACEStatusCounter OBJECT-TYPE
   SYNTAX      Counter32
   MAX-ACCESS  read-only
   STATUS      current
   DESCRIPTION
       " The counter indicates the number of times the ACE was hit by a frame. "
   ::= { gel2esw10gACLACEStatusEntry 11 }
   
gel2esw10gACLACEStatusConflict OBJECT-TYPE
   SYNTAX      DisplayString
   MAX-ACCESS  read-only
   STATUS      current
   DESCRIPTION
       " Indicates the hardware status of the specific ACE. The specific ACE is not applied to the hardware due to hardware limitations. "
   ::= { gel2esw10gACLACEStatusEntry 12 }


----------------------------------------------------------------------------------------------------------------------------
gel2esw10gSecurity                                              OBJECT IDENTIFIER ::= { gel2esw10gProductId 3 }

gel2esw10gIPSourceGuard                                         OBJECT IDENTIFIER ::= { gel2esw10gSecurity 1 }

gel2esw10gIPSourceGuardConf                                     OBJECT IDENTIFIER ::= { gel2esw10gIPSourceGuard 1 }

gel2esw10gIPSourceGuardMode OBJECT-TYPE
   SYNTAX      INTEGER (0|1)
   MAX-ACCESS  read-write
   STATUS      current
   DESCRIPTION
       " default:  0
        0: disable
        1: enable"
   ::= { gel2esw10gIPSourceGuardConf 1 }

gel2esw10gIPSourceGuardPortConfigTable OBJECT-TYPE
   SYNTAX      SEQUENCE OF GEL2ESW10GIPSourceGuardPortConfigEntry
   MAX-ACCESS  not-accessible
   STATUS      current
   DESCRIPTION
       " "
   ::= { gel2esw10gIPSourceGuardConf 2 }

gel2esw10gIPSourceGuardPortConfigEntry OBJECT-TYPE
   SYNTAX      GEL2ESW10GIPSourceGuardPortConfigEntry
   MAX-ACCESS  not-accessible
   STATUS      current
   DESCRIPTION
       ""
   INDEX    { gel2esw10gIPSourceGuardPortConfigPort  }
   ::= { gel2esw10gIPSourceGuardPortConfigTable 1 }

GEL2ESW10GIPSourceGuardPortConfigEntry ::= SEQUENCE {
   gel2esw10gIPSourceGuardPortConfigPort               INTEGER,
   gel2esw10gIPSourceGuardPortConfigMode               INTEGER,
   gel2esw10gIPSourceGuardPortMaxDynamicClients        INTEGER
}

gel2esw10gIPSourceGuardPortConfigPort OBJECT-TYPE
   SYNTAX      INTEGER (1..4095)
   MAX-ACCESS  not-accessible
   STATUS      current
   DESCRIPTION
       " "
   ::= { gel2esw10gIPSourceGuardPortConfigEntry 1 }

gel2esw10gIPSourceGuardPortConfigMode OBJECT-TYPE
   SYNTAX      INTEGER (0|1)
   MAX-ACCESS  read-write
   STATUS      current
   DESCRIPTION
       "default: 0
       0:disable
       1:enable "
   ::= { gel2esw10gIPSourceGuardPortConfigEntry 2 }

gel2esw10gIPSourceGuardPortMaxDynamicClients OBJECT-TYPE
   SYNTAX      INTEGER (0..2|99)
   MAX-ACCESS  read-write
   STATUS      current
   DESCRIPTION
       "default: 99
       0~2: Max Dynamic clients
       99:Unlimited "
   ::= { gel2esw10gIPSourceGuardPortConfigEntry 3 }


gel2esw10gIPSourceGuardStatic                                OBJECT IDENTIFIER ::= { gel2esw10gIPSourceGuard 2 }

gel2esw10gIPSourceGuardStaticCreate OBJECT-TYPE
   SYNTAX       INTEGER(0|1)
   MAX-ACCESS   read-write
   STATUS       current
   DESCRIPTION
       "default: 0
        0 : None  (read only)
        1 : Create a IP Source Guard"
   ::= { gel2esw10gIPSourceGuardStatic 1 }

gel2esw10gIPSourceGuardStaticTable OBJECT-TYPE
   SYNTAX      SEQUENCE OF GEL2ESW10GIPSourceGuardStaticEntry
   MAX-ACCESS  not-accessible
   STATUS      current
   DESCRIPTION
       " "
   ::= { gel2esw10gIPSourceGuardStatic 2 }

gel2esw10gIPSourceGuardStaticEntry OBJECT-TYPE
   SYNTAX      GEL2ESW10GIPSourceGuardStaticEntry
   MAX-ACCESS  not-accessible
   STATUS      current
   DESCRIPTION
       ""
   INDEX    { gel2esw10gIPSourceGuardStaticIndex  }
   ::= { gel2esw10gIPSourceGuardStaticTable 1 }

GEL2ESW10GIPSourceGuardStaticEntry ::= SEQUENCE {
   gel2esw10gIPSourceGuardStaticIndex         INTEGER,
   gel2esw10gIPSourceGuardStaticPort          INTEGER,
   gel2esw10gIPSourceGuardStaticVLANId        INTEGER,
   gel2esw10gIPSourceGuardStaticIPAddress     IpAddress,
   gel2esw10gIPSourceGuardStaticMACAddress    MacAddress,
   gel2esw10gIPSourceGuardStaticRowStatus     INTEGER
}

gel2esw10gIPSourceGuardStaticIndex OBJECT-TYPE
   SYNTAX      INTEGER (1..28)
   MAX-ACCESS  not-accessible
   STATUS      current
   DESCRIPTION
       " "
   ::= { gel2esw10gIPSourceGuardStaticEntry 1 }

gel2esw10gIPSourceGuardStaticPort OBJECT-TYPE
   SYNTAX      INTEGER (1..4095)
   MAX-ACCESS  read-write
   STATUS      current
   DESCRIPTION
       " Port, range: 1 - port number. "
   ::= { gel2esw10gIPSourceGuardStaticEntry 2 }

gel2esw10gIPSourceGuardStaticVLANId OBJECT-TYPE
   SYNTAX      INTEGER (1..4094)
   MAX-ACCESS  read-write
   STATUS      current
   DESCRIPTION
       " VLAN ID, range: 1 - 4094. "
   ::= { gel2esw10gIPSourceGuardStaticEntry 3 }

gel2esw10gIPSourceGuardStaticIPAddress OBJECT-TYPE
   SYNTAX      IpAddress
   MAX-ACCESS  read-write
   STATUS      current
   DESCRIPTION
       " IP address allowed for doing IP source guard. "
   ::= { gel2esw10gIPSourceGuardStaticEntry 4 }

gel2esw10gIPSourceGuardStaticMACAddress OBJECT-TYPE
   SYNTAX      MacAddress
   MAX-ACCESS  read-write
   STATUS      current
   DESCRIPTION
       " Allowed Source MAC address, format 0a 1b 2c 3d 4e 5f "
   ::= { gel2esw10gIPSourceGuardStaticEntry 5 }

gel2esw10gIPSourceGuardStaticRowStatus OBJECT-TYPE
   SYNTAX      INTEGER (1..5)
   MAX-ACCESS  read-write
   STATUS      current
   DESCRIPTION
       "1: active
        2: notInservice
        3: edit
        4: destroy
        5: undo"
   ::= { gel2esw10gIPSourceGuardStaticEntry 6 }

gel2esw10gIPSourceGuardDynamicTable OBJECT-TYPE
   SYNTAX      SEQUENCE OF GEL2ESW10GIPSourceGuardDynamicEntry
   MAX-ACCESS  not-accessible
   STATUS      current
   DESCRIPTION
       " "
   ::= { gel2esw10gIPSourceGuard 3 }

gel2esw10gIPSourceGuardDynamicEntry OBJECT-TYPE
   SYNTAX      GEL2ESW10GIPSourceGuardDynamicEntry
   MAX-ACCESS  not-accessible
   STATUS      current
   DESCRIPTION
       ""
   INDEX    { gel2esw10gIPSourceGuardDynamicIndex  }
   ::= { gel2esw10gIPSourceGuardDynamicTable 1 }

GEL2ESW10GIPSourceGuardDynamicEntry ::= SEQUENCE {
   gel2esw10gIPSourceGuardDynamicIndex          INTEGER,
   gel2esw10gIPSourceGuardDynamicPort           INTEGER,
   gel2esw10gIPSourceGuardDynamicVLANId         INTEGER,
   gel2esw10gIPSourceGuardDynamicIPAddress      IpAddress,
   gel2esw10gIPSourceGuardDynamicMACAddress     MacAddress
}

gel2esw10gIPSourceGuardDynamicIndex OBJECT-TYPE
   SYNTAX      INTEGER(1..4095)
   MAX-ACCESS  not-accessible
   STATUS      current
   DESCRIPTION
       " "
   ::= { gel2esw10gIPSourceGuardDynamicEntry 1 }

gel2esw10gIPSourceGuardDynamicPort OBJECT-TYPE
   SYNTAX      INTEGER (1..10)
   MAX-ACCESS  read-only
   STATUS      current
   DESCRIPTION
       " "
   ::= { gel2esw10gIPSourceGuardDynamicEntry 2 }

gel2esw10gIPSourceGuardDynamicVLANId OBJECT-TYPE
   SYNTAX      INTEGER (1..4094)
   MAX-ACCESS  read-only
   STATUS      current
   DESCRIPTION
       " "
   ::= { gel2esw10gIPSourceGuardDynamicEntry 3 }

gel2esw10gIPSourceGuardDynamicIPAddress OBJECT-TYPE
   SYNTAX      IpAddress
   MAX-ACCESS  read-only
   STATUS      current
   DESCRIPTION
       " "
   ::= { gel2esw10gIPSourceGuardDynamicEntry 4 }

gel2esw10gIPSourceGuardDynamicMACAddress OBJECT-TYPE
   SYNTAX      MacAddress
   MAX-ACCESS  read-only
   STATUS      current
   DESCRIPTION
       " "
   ::= { gel2esw10gIPSourceGuardDynamicEntry 5 }

gel2esw10gARPInspection                                         OBJECT IDENTIFIER ::= { gel2esw10gSecurity 2 }

gel2esw10gARPInspectionConf                                     OBJECT IDENTIFIER ::= { gel2esw10gARPInspection 1 }

gel2esw10gARPInspectionConfMode OBJECT-TYPE
   SYNTAX      INTEGER(0|1)
   MAX-ACCESS  read-write
   STATUS      current
   DESCRIPTION
       "default: 0
        0: disable
        1: enable"
   ::= { gel2esw10gARPInspectionConf 1 }

gel2esw10gARPInspectionConfTable OBJECT-TYPE
   SYNTAX      SEQUENCE OF GEL2ESW10GARPInspectionConfEntry
   MAX-ACCESS  not-accessible
   STATUS      current
   DESCRIPTION
       " "
   ::= { gel2esw10gARPInspectionConf 2 }

gel2esw10gARPInspectionConfEntry OBJECT-TYPE
   SYNTAX      GEL2ESW10GARPInspectionConfEntry
   MAX-ACCESS  not-accessible
   STATUS      current
   DESCRIPTION
       ""
   INDEX    { gel2esw10gARPInspectionConfPortIndex  }
   ::= { gel2esw10gARPInspectionConfTable 1 }

GEL2ESW10GARPInspectionConfEntry ::= SEQUENCE {
   gel2esw10gARPInspectionConfPortIndex	INTEGER,
   gel2esw10gARPInspectionConfPortMode	INTEGER
}

gel2esw10gARPInspectionConfPortIndex OBJECT-TYPE
   SYNTAX      INTEGER(1..4095)
   MAX-ACCESS  not-accessible
   STATUS      current
   DESCRIPTION
       " "
   ::= { gel2esw10gARPInspectionConfEntry 1 }

gel2esw10gARPInspectionConfPortMode OBJECT-TYPE
   SYNTAX      INTEGER (0|1)
   MAX-ACCESS  read-write
   STATUS      current
   DESCRIPTION
       "default: 0
        0: disable
        1: enable"
   ::= { gel2esw10gARPInspectionConfEntry 2 }


gel2esw10gARPInspectionStatic                                OBJECT IDENTIFIER ::= { gel2esw10gARPInspection 2 }

gel2esw10gARPInspectionStaticCreate OBJECT-TYPE
   SYNTAX      INTEGER (0|1)
   MAX-ACCESS  read-write
   STATUS      current
   DESCRIPTION
       "default: 0
        0: none
        1: create"
   ::= { gel2esw10gARPInspectionStatic 1 }

gel2esw10gARPInspectionStaticTable OBJECT-TYPE
   SYNTAX      SEQUENCE OF GEL2ESW10GARPInspectionStaticEntry
   MAX-ACCESS  not-accessible
   STATUS      current
   DESCRIPTION
       " "
   ::= { gel2esw10gARPInspectionStatic 2 }

gel2esw10gARPInspectionStaticEntry OBJECT-TYPE
   SYNTAX      GEL2ESW10GARPInspectionStaticEntry
   MAX-ACCESS  not-accessible
   STATUS      current
   DESCRIPTION
       ""
   INDEX    { gel2esw10gARPInspectionStaticIndex  }
   ::= { gel2esw10gARPInspectionStaticTable 1 }

GEL2ESW10GARPInspectionStaticEntry ::= SEQUENCE {
   gel2esw10gARPInspectionStaticIndex       INTEGER,
   gel2esw10gARPInspectionStaticPort        INTEGER,
   gel2esw10gARPInspectionStaticVLANId      INTEGER,
   gel2esw10gARPInspectionStaticIPAddress   IpAddress,
   gel2esw10gARPInspectionStaticMACAddress  MacAddress,
   gel2esw10gARPInspectionStaticRowStatus   INTEGER
}

gel2esw10gARPInspectionStaticIndex OBJECT-TYPE
   SYNTAX      INTEGER(1..4095)
   MAX-ACCESS  not-accessible
   STATUS      current
   DESCRIPTION
       ""
   ::= { gel2esw10gARPInspectionStaticEntry 1 }

gel2esw10gARPInspectionStaticPort OBJECT-TYPE
   SYNTAX      INTEGER(1..4095)
   MAX-ACCESS  read-write
   STATUS      current
   DESCRIPTION
       " Port, range: 1 - port number. "
   ::= { gel2esw10gARPInspectionStaticEntry 2 }

gel2esw10gARPInspectionStaticVLANId OBJECT-TYPE
   SYNTAX      INTEGER (1..4094)
   MAX-ACCESS  read-write
   STATUS      current
   DESCRIPTION
       " VLAN ID, range: 1 - 4094. "
   ::= { gel2esw10gARPInspectionStaticEntry 3 }

gel2esw10gARPInspectionStaticIPAddress OBJECT-TYPE
   SYNTAX      IpAddress
   MAX-ACCESS  read-write
   STATUS      current
   DESCRIPTION
       " IP address allowed for doing ARP request. "
   ::= { gel2esw10gARPInspectionStaticEntry 4 }

gel2esw10gARPInspectionStaticMACAddress OBJECT-TYPE
   SYNTAX      MacAddress
   MAX-ACCESS  read-write
   STATUS      current
   DESCRIPTION
       " Allowed Source MAC address in ARP request packets, format 0a 1b 2c 3d 4e 5f "
   ::= { gel2esw10gARPInspectionStaticEntry 5 }

gel2esw10gARPInspectionStaticRowStatus OBJECT-TYPE
   SYNTAX      INTEGER(1..5)
   MAX-ACCESS  read-write
   STATUS      current
   DESCRIPTION
       "1: active
        2: notInservice
        3: edit
        4: destroy
        5: undo"
   ::= { gel2esw10gARPInspectionStaticEntry 6 }

gel2esw10gARPInspectionDynamicTable OBJECT-TYPE
   SYNTAX      SEQUENCE OF GEL2ESW10GARPInspectionDynamicEntry
   MAX-ACCESS  not-accessible
   STATUS      current
   DESCRIPTION
       " "
   ::= { gel2esw10gARPInspection 3 }

gel2esw10gARPInspectionDynamicEntry OBJECT-TYPE
   SYNTAX      GEL2ESW10GARPInspectionDynamicEntry
   MAX-ACCESS  not-accessible
   STATUS      current
   DESCRIPTION
       ""
   INDEX    { gel2esw10gARPInspectionDynamicIndex  }
   ::= { gel2esw10gARPInspectionDynamicTable 1 }

GEL2ESW10GARPInspectionDynamicEntry ::= SEQUENCE {
   gel2esw10gARPInspectionDynamicIndex          INTEGER,
   gel2esw10gARPInspectionDynamicPort           INTEGER,
   gel2esw10gARPInspectionDynamicVLANId         INTEGER,
   gel2esw10gARPInspectionDynamicIPAddress      IpAddress,
   gel2esw10gARPInspectionDynamicMACAddress     MacAddress
}

gel2esw10gARPInspectionDynamicIndex OBJECT-TYPE
   SYNTAX      INTEGER(1..4095)
   MAX-ACCESS  not-accessible
   STATUS      current
   DESCRIPTION
       " "
   ::= { gel2esw10gARPInspectionDynamicEntry 1 }

gel2esw10gARPInspectionDynamicPort OBJECT-TYPE
   SYNTAX      INTEGER(1..4095)
   MAX-ACCESS  read-only
   STATUS      current
   DESCRIPTION
       ""
   ::= { gel2esw10gARPInspectionDynamicEntry 2 }

gel2esw10gARPInspectionDynamicVLANId OBJECT-TYPE
   SYNTAX      INTEGER (1..4094)
   MAX-ACCESS  read-only
   STATUS      current
   DESCRIPTION
       ""
   ::= { gel2esw10gARPInspectionDynamicEntry 3 }

gel2esw10gARPInspectionDynamicIPAddress OBJECT-TYPE
   SYNTAX      IpAddress
   MAX-ACCESS  read-only
   STATUS      current
   DESCRIPTION
       ""
   ::= { gel2esw10gARPInspectionDynamicEntry 4 }

gel2esw10gARPInspectionDynamicMACAddress OBJECT-TYPE
   SYNTAX      MacAddress
   MAX-ACCESS  read-only
   STATUS      current
   DESCRIPTION
       ""
   ::= { gel2esw10gARPInspectionDynamicEntry 5 }

gel2esw10gDHCPSnooping                                          OBJECT IDENTIFIER ::= { gel2esw10gSecurity 3 }

gel2esw10gDHCPSnoopingConf                                          OBJECT IDENTIFIER ::= { gel2esw10gDHCPSnooping 1 }

gel2esw10gDHCPSnoopingMode OBJECT-TYPE
   SYNTAX      INTEGER(0|1)
   MAX-ACCESS  read-write
   STATUS      current
   DESCRIPTION
       "default: 0
       0: disable
       1: enable"
   ::= { gel2esw10gDHCPSnoopingConf 1 }

gel2esw10gDHCPSnoopingPortModeConfigurationTable OBJECT-TYPE
   SYNTAX      SEQUENCE OF GEL2ESW10GDHCPSnoopingPortModeConfigurationEntry
   MAX-ACCESS  not-accessible
   STATUS      current
   DESCRIPTION
       " "
   ::= { gel2esw10gDHCPSnoopingConf 2 }

gel2esw10gDHCPSnoopingPortModeConfigurationEntry OBJECT-TYPE
   SYNTAX      GEL2ESW10GDHCPSnoopingPortModeConfigurationEntry
   MAX-ACCESS  not-accessible
   STATUS      current
   DESCRIPTION
       ""
   INDEX    { gel2esw10gDHCPSnoopingPortModeConfigurationPort  }
   ::= { gel2esw10gDHCPSnoopingPortModeConfigurationTable 1 }
   
GEL2ESW10GDHCPSnoopingPortModeConfigurationEntry ::= SEQUENCE {
   gel2esw10gDHCPSnoopingPortModeConfigurationPort	INTEGER,
   gel2esw10gDHCPSnoopingPortModeConfigurationMode	INTEGER
}

gel2esw10gDHCPSnoopingPortModeConfigurationPort OBJECT-TYPE
   SYNTAX      INTEGER(1..4095)
   MAX-ACCESS  not-accessible
   STATUS      current
   DESCRIPTION
       " "
   ::= { gel2esw10gDHCPSnoopingPortModeConfigurationEntry 1 }

gel2esw10gDHCPSnoopingPortModeConfigurationMode OBJECT-TYPE
   SYNTAX      INTEGER (0|1)
   MAX-ACCESS  read-write
   STATUS      current
   DESCRIPTION
       "default: 1
       0: trust port mode
       1: untrust port mode"
   ::= { gel2esw10gDHCPSnoopingPortModeConfigurationEntry 2 }

gel2esw10gDHCPSnoopingStatisticsTable OBJECT-TYPE
   SYNTAX      SEQUENCE OF GEL2ESW10GDHCPSnoopingStatisticsEntry
   MAX-ACCESS  not-accessible
   STATUS      current
   DESCRIPTION
       " "
   ::= { gel2esw10gDHCPSnooping 2 }

gel2esw10gDHCPSnoopingStatisticsEntry OBJECT-TYPE
   SYNTAX      GEL2ESW10GDHCPSnoopingStatisticsEntry
   MAX-ACCESS  not-accessible
   STATUS      current
   DESCRIPTION
       ""
   INDEX    { gel2esw10gDHCPSnoopingStatisticsPort  }
   ::= { gel2esw10gDHCPSnoopingStatisticsTable 1 }

GEL2ESW10GDHCPSnoopingStatisticsEntry ::= SEQUENCE {
   gel2esw10gDHCPSnoopingStatisticsPort         INTEGER,
   gel2esw10gDHCPSnoopingStatisticsClear        INTEGER,
   gel2esw10gDHCPSnoopingRxDiscover             Counter32,
   gel2esw10gDHCPSnoopingRxOffer                Counter32,
   gel2esw10gDHCPSnoopingRxRequest              Counter32,
   gel2esw10gDHCPSnoopingRxDecline              Counter32,
   gel2esw10gDHCPSnoopingRxACK                  Counter32,
   gel2esw10gDHCPSnoopingRxNAK                  Counter32,
   gel2esw10gDHCPSnoopingRxRelease              Counter32,
   gel2esw10gDHCPSnoopingRxInform               Counter32,
   gel2esw10gDHCPSnoopingRxLeaseQuery           Counter32,
   gel2esw10gDHCPSnoopingRxLeaseUnassigned      Counter32,
   gel2esw10gDHCPSnoopingRxLeaseUnknown         Counter32,
   gel2esw10gDHCPSnoopingRxLeaseActive          Counter32,
   gel2esw10gDHCPSnoopingTxDiscover             Counter32,
   gel2esw10gDHCPSnoopingTxOffer                Counter32,
   gel2esw10gDHCPSnoopingTxRequest              Counter32,
   gel2esw10gDHCPSnoopingTxDecline              Counter32,
   gel2esw10gDHCPSnoopingTxACK                  Counter32,
   gel2esw10gDHCPSnoopingTxNAK                  Counter32,
   gel2esw10gDHCPSnoopingTxRelease              Counter32,
   gel2esw10gDHCPSnoopingTxInform               Counter32,
   gel2esw10gDHCPSnoopingTxLeaseQuery           Counter32,
   gel2esw10gDHCPSnoopingTxLeaseUnassigned      Counter32,
   gel2esw10gDHCPSnoopingTxLeaseUnknown         Counter32,
   gel2esw10gDHCPSnoopingTxLeaseActive          Counter32
}

gel2esw10gDHCPSnoopingStatisticsPort OBJECT-TYPE
   SYNTAX      INTEGER(1..4095)
   MAX-ACCESS  not-accessible
   STATUS      current
   DESCRIPTION
       " "
   ::= { gel2esw10gDHCPSnoopingStatisticsEntry 1 }

gel2esw10gDHCPSnoopingStatisticsClear OBJECT-TYPE
   SYNTAX      INTEGER (0|1)
   MAX-ACCESS  read-write
   STATUS      current
   DESCRIPTION
       "default: 0
       0: none
       1: clear"
   ::= { gel2esw10gDHCPSnoopingStatisticsEntry 2 }
   
gel2esw10gDHCPSnoopingRxDiscover OBJECT-TYPE
   SYNTAX      Counter32
   MAX-ACCESS  read-only
   STATUS      current
   DESCRIPTION
       " "
   ::= { gel2esw10gDHCPSnoopingStatisticsEntry 3 }

gel2esw10gDHCPSnoopingRxOffer OBJECT-TYPE
   SYNTAX      Counter32
   MAX-ACCESS  read-only
   STATUS      current
   DESCRIPTION
       " "
   ::= { gel2esw10gDHCPSnoopingStatisticsEntry 4 }

gel2esw10gDHCPSnoopingRxRequest OBJECT-TYPE
   SYNTAX      Counter32
   MAX-ACCESS  read-only
   STATUS      current
   DESCRIPTION
       " "
   ::= { gel2esw10gDHCPSnoopingStatisticsEntry 5 }

gel2esw10gDHCPSnoopingRxDecline OBJECT-TYPE
   SYNTAX      Counter32
   MAX-ACCESS  read-only
   STATUS      current
   DESCRIPTION
       " "
   ::= { gel2esw10gDHCPSnoopingStatisticsEntry 6 }

gel2esw10gDHCPSnoopingRxACK OBJECT-TYPE
   SYNTAX      Counter32
   MAX-ACCESS  read-only
   STATUS      current
   DESCRIPTION
       " "
   ::= { gel2esw10gDHCPSnoopingStatisticsEntry 7 }

gel2esw10gDHCPSnoopingRxNAK OBJECT-TYPE
   SYNTAX      Counter32
   MAX-ACCESS  read-only
   STATUS      current
   DESCRIPTION
       " "
   ::= { gel2esw10gDHCPSnoopingStatisticsEntry 8 }   

gel2esw10gDHCPSnoopingRxRelease OBJECT-TYPE
   SYNTAX      Counter32
   MAX-ACCESS  read-only
   STATUS      current
   DESCRIPTION
       " "
   ::= { gel2esw10gDHCPSnoopingStatisticsEntry 9 }

gel2esw10gDHCPSnoopingRxInform OBJECT-TYPE
   SYNTAX      Counter32
   MAX-ACCESS  read-only
   STATUS      current
   DESCRIPTION
       " "
   ::= { gel2esw10gDHCPSnoopingStatisticsEntry 10 }

gel2esw10gDHCPSnoopingRxLeaseQuery OBJECT-TYPE
   SYNTAX      Counter32
   MAX-ACCESS  read-only
   STATUS      current
   DESCRIPTION
       " "
   ::= { gel2esw10gDHCPSnoopingStatisticsEntry 11 }

gel2esw10gDHCPSnoopingRxLeaseUnassigned OBJECT-TYPE
   SYNTAX      Counter32
   MAX-ACCESS  read-only
   STATUS      current
   DESCRIPTION
       " "
   ::= { gel2esw10gDHCPSnoopingStatisticsEntry 12 }

gel2esw10gDHCPSnoopingRxLeaseUnknown OBJECT-TYPE
   SYNTAX      Counter32
   MAX-ACCESS  read-only
   STATUS      current
   DESCRIPTION
       " "
   ::= { gel2esw10gDHCPSnoopingStatisticsEntry 13 }

gel2esw10gDHCPSnoopingRxLeaseActive OBJECT-TYPE
   SYNTAX      Counter32
   MAX-ACCESS  read-only
   STATUS      current
   DESCRIPTION
       " "
   ::= { gel2esw10gDHCPSnoopingStatisticsEntry 14 }

gel2esw10gDHCPSnoopingTxDiscover OBJECT-TYPE
   SYNTAX      Counter32
   MAX-ACCESS  read-only
   STATUS      current
   DESCRIPTION
       " "
   ::= { gel2esw10gDHCPSnoopingStatisticsEntry 15 }

gel2esw10gDHCPSnoopingTxOffer OBJECT-TYPE
   SYNTAX      Counter32
   MAX-ACCESS  read-only
   STATUS      current
   DESCRIPTION
       " "
   ::= { gel2esw10gDHCPSnoopingStatisticsEntry 16 }

gel2esw10gDHCPSnoopingTxRequest OBJECT-TYPE
   SYNTAX      Counter32
   MAX-ACCESS  read-only
   STATUS      current
   DESCRIPTION
       " "
   ::= { gel2esw10gDHCPSnoopingStatisticsEntry 17 }

gel2esw10gDHCPSnoopingTxDecline OBJECT-TYPE
   SYNTAX      Counter32
   MAX-ACCESS  read-only
   STATUS      current
   DESCRIPTION
       " "
   ::= { gel2esw10gDHCPSnoopingStatisticsEntry 18 }

gel2esw10gDHCPSnoopingTxACK OBJECT-TYPE
   SYNTAX      Counter32
   MAX-ACCESS  read-only
   STATUS      current
   DESCRIPTION
       " "
   ::= { gel2esw10gDHCPSnoopingStatisticsEntry 19 }

gel2esw10gDHCPSnoopingTxNAK OBJECT-TYPE
   SYNTAX      Counter32
   MAX-ACCESS  read-only
   STATUS      current
   DESCRIPTION
       " "
   ::= { gel2esw10gDHCPSnoopingStatisticsEntry 20 }   

gel2esw10gDHCPSnoopingTxRelease OBJECT-TYPE
   SYNTAX      Counter32
   MAX-ACCESS  read-only
   STATUS      current
   DESCRIPTION
       " "
   ::= { gel2esw10gDHCPSnoopingStatisticsEntry 21 }

gel2esw10gDHCPSnoopingTxInform OBJECT-TYPE
   SYNTAX      Counter32
   MAX-ACCESS  read-only
   STATUS      current
   DESCRIPTION
       " "
   ::= { gel2esw10gDHCPSnoopingStatisticsEntry 22 }

gel2esw10gDHCPSnoopingTxLeaseQuery OBJECT-TYPE
   SYNTAX      Counter32
   MAX-ACCESS  read-only
   STATUS      current
   DESCRIPTION
       " "
   ::= { gel2esw10gDHCPSnoopingStatisticsEntry 23 }

gel2esw10gDHCPSnoopingTxLeaseUnassigned OBJECT-TYPE
   SYNTAX      Counter32
   MAX-ACCESS  read-only
   STATUS      current
   DESCRIPTION
       " "
   ::= { gel2esw10gDHCPSnoopingStatisticsEntry 24 }

gel2esw10gDHCPSnoopingTxLeaseUnknown OBJECT-TYPE
   SYNTAX      Counter32
   MAX-ACCESS  read-only
   STATUS      current
   DESCRIPTION
       " "
   ::= { gel2esw10gDHCPSnoopingStatisticsEntry 25 }

gel2esw10gDHCPSnoopingTxLeaseActive OBJECT-TYPE
   SYNTAX      Counter32
   MAX-ACCESS  read-only
   STATUS      current
   DESCRIPTION
       " "
   ::= { gel2esw10gDHCPSnoopingStatisticsEntry 26 }


gel2esw10gDHCPRelay                                             OBJECT IDENTIFIER ::= { gel2esw10gSecurity 4 }

gel2esw10gDHCPRelayConfiguration                                         OBJECT IDENTIFIER ::= { gel2esw10gDHCPRelay 1 }

gel2esw10gDHCPRelayMode OBJECT-TYPE
   SYNTAX      INTEGER(0|1)
   MAX-ACCESS  read-write
   STATUS      current
   DESCRIPTION
       "default: 0
       0: disable
       1: enable 
       We need at least one server"
   ::= { gel2esw10gDHCPRelayConfiguration 1 }

gel2esw10gDHCPRelayServer OBJECT-TYPE
   SYNTAX      IpAddress
   MAX-ACCESS  read-write
   STATUS      current
   DESCRIPTION
       " "
   ::= { gel2esw10gDHCPRelayConfiguration 2 }

gel2esw10gDHCPRelayInformationMode OBJECT-TYPE
   SYNTAX      INTEGER(0|1)
   MAX-ACCESS  read-write
   STATUS      current
   DESCRIPTION
       "default: 0
       0: disable
       1: enable "
   ::= { gel2esw10gDHCPRelayConfiguration 3 }

gel2esw10gDHCPRelayInformationPolicy OBJECT-TYPE
   SYNTAX      INTEGER(0..2)
   MAX-ACCESS  read-write
   STATUS      current
   DESCRIPTION
       "default: 0
       0: replace
       1: keep
       2: drop "
   ::= { gel2esw10gDHCPRelayConfiguration 4 }

gel2esw10gDHCPRelayStatistics                                   OBJECT IDENTIFIER ::= { gel2esw10gDHCPRelay 2 }

gel2esw10gDHCPRelayServerStatistics                                   OBJECT IDENTIFIER ::= { gel2esw10gDHCPRelayStatistics 1 }

gel2esw10gServerStatTransmitToServer OBJECT-TYPE
   SYNTAX      Counter32
   MAX-ACCESS  read-only
   STATUS      current
   DESCRIPTION
       " "
   ::= { gel2esw10gDHCPRelayServerStatistics 1 }

gel2esw10gServerStatTransmitError OBJECT-TYPE
   SYNTAX      Counter32
   MAX-ACCESS  read-only
   STATUS      current
   DESCRIPTION
       " "
   ::= { gel2esw10gDHCPRelayServerStatistics 2 }

gel2esw10gServerStatReceiveFromServer OBJECT-TYPE
   SYNTAX      Counter32
   MAX-ACCESS  read-only
   STATUS      current
   DESCRIPTION
       " "
   ::= { gel2esw10gDHCPRelayServerStatistics 3 }

gel2esw10gServerStatReceiveMissingAgentOption OBJECT-TYPE
   SYNTAX      Counter32
   MAX-ACCESS  read-only
   STATUS      current
   DESCRIPTION
       " "
   ::= { gel2esw10gDHCPRelayServerStatistics 4 }

gel2esw10gServerStatReceiveMissingCircuitID OBJECT-TYPE
   SYNTAX      Counter32
   MAX-ACCESS  read-only
   STATUS      current
   DESCRIPTION
       " "
   ::= { gel2esw10gDHCPRelayServerStatistics 5 }

gel2esw10gServerStatReceiveMissingRemoteID OBJECT-TYPE
   SYNTAX      Counter32
   MAX-ACCESS  read-only
   STATUS      current
   DESCRIPTION
       " "
   ::= { gel2esw10gDHCPRelayServerStatistics 6 }

gel2esw10gServerStatReceiveBadCircuitID OBJECT-TYPE
   SYNTAX      Counter32
   MAX-ACCESS  read-only
   STATUS      current
   DESCRIPTION
       " "
   ::= { gel2esw10gDHCPRelayServerStatistics 7 }

gel2esw10gServerStatReceiveBadRemoteID OBJECT-TYPE
   SYNTAX      Counter32
   MAX-ACCESS  read-only
   STATUS      current
   DESCRIPTION
       " "
   ::= { gel2esw10gDHCPRelayServerStatistics 8 }

gel2esw10gDHCPRelayClientStatistics                                   OBJECT IDENTIFIER ::= { gel2esw10gDHCPRelayStatistics 2 }

gel2esw10gClientStatTransmitToClient OBJECT-TYPE
   SYNTAX      Counter32
   MAX-ACCESS  read-only
   STATUS      current
   DESCRIPTION
       " "
   ::= { gel2esw10gDHCPRelayClientStatistics 1 }

gel2esw10gClientStatTransmitError OBJECT-TYPE
   SYNTAX      Counter32
   MAX-ACCESS  read-only
   STATUS      current
   DESCRIPTION
       " "
   ::= { gel2esw10gDHCPRelayClientStatistics 2 }

gel2esw10gClientStatReceivefromClient OBJECT-TYPE
   SYNTAX      Counter32
   MAX-ACCESS  read-only
   STATUS      current
   DESCRIPTION
       " "
   ::= { gel2esw10gDHCPRelayClientStatistics 3 }

gel2esw10gClientStatReceiveAgentOption OBJECT-TYPE
   SYNTAX      Counter32
   MAX-ACCESS  read-only
   STATUS      current
   DESCRIPTION
       " "
   ::= { gel2esw10gDHCPRelayClientStatistics 4 }

gel2esw10gClientStatReplaceAgentOption OBJECT-TYPE
   SYNTAX      Counter32
   MAX-ACCESS  read-only
   STATUS      current
   DESCRIPTION
       " "
   ::= { gel2esw10gDHCPRelayClientStatistics 5 }

gel2esw10gClientStatKeepAgentOption OBJECT-TYPE
   SYNTAX      Counter32
   MAX-ACCESS  read-only
   STATUS      current
   DESCRIPTION
       " "
   ::= { gel2esw10gDHCPRelayClientStatistics 6 }

gel2esw10gClientStatDropAgentOption OBJECT-TYPE
   SYNTAX      Counter32
   MAX-ACCESS  read-only
   STATUS      current
   DESCRIPTION
       " "
   ::= { gel2esw10gDHCPRelayClientStatistics 7 }

gel2esw10gPortSecurity                                          OBJECT IDENTIFIER ::= { gel2esw10gSecurity 5 }

gel2esw10gPortSecLimitCtrl                                      OBJECT IDENTIFIER ::= { gel2esw10gPortSecurity 1 }

gel2esw10gPortSecLimitCtrlSystemConf                                      OBJECT IDENTIFIER ::= { gel2esw10gPortSecLimitCtrl 1 }

gel2esw10gPortSecurityMode OBJECT-TYPE
   SYNTAX      INTEGER(0|1)
   MAX-ACCESS  read-write
   STATUS      current
   DESCRIPTION
       "default: 0
       0: disable
       1: enable "
   ::= { gel2esw10gPortSecLimitCtrlSystemConf 1 }

gel2esw10gPortSecurityAging OBJECT-TYPE
   SYNTAX      INTEGER(0|1)
   MAX-ACCESS  read-write
   STATUS      current
   DESCRIPTION
       "default: 0
       0: disable
       1: enable "
   ::= { gel2esw10gPortSecLimitCtrlSystemConf 2 }

gel2esw10gPortSecurityAgingPeriod OBJECT-TYPE
   SYNTAX      INTEGER(10..10000000)
   MAX-ACCESS  read-write
   STATUS      current
   DESCRIPTION
       "default: 3600, range: 10-10000000 "
   ::= { gel2esw10gPortSecLimitCtrlSystemConf 3 }

gel2esw10gPortSecLimitCtrlTable OBJECT-TYPE
   SYNTAX      SEQUENCE OF GEL2ESW10GPortSecLimitCtrlEntry
   MAX-ACCESS  not-accessible
   STATUS      current
   DESCRIPTION
       " "
   ::= { gel2esw10gPortSecLimitCtrl 2 }

gel2esw10gPortSecLimitCtrlEntry OBJECT-TYPE
   SYNTAX      GEL2ESW10GPortSecLimitCtrlEntry
   MAX-ACCESS  not-accessible
   STATUS      current
   DESCRIPTION
       ""
   INDEX    { gel2esw10gPortSecLimitCtrlPort  }
   ::= { gel2esw10gPortSecLimitCtrlTable 1 }

GEL2ESW10GPortSecLimitCtrlEntry ::= SEQUENCE {
   gel2esw10gPortSecLimitCtrlPort           INTEGER,
   gel2esw10gPortSecLimitCtrlPortMode       INTEGER,
   gel2esw10gPortSecLimitCtrlPortLimit      INTEGER,
   gel2esw10gPortSecLimitCtrlPortAction     INTEGER,
   gel2esw10gPortSecLimitCtrlPortState      DisplayString,
   gel2esw10gPortSecLimitCtrlPortReOpen     INTEGER
}

gel2esw10gPortSecLimitCtrlPort OBJECT-TYPE
   SYNTAX      INTEGER (1..4095)
   MAX-ACCESS  not-accessible
   STATUS      current
   DESCRIPTION
       " "
   ::= { gel2esw10gPortSecLimitCtrlEntry 1 }

gel2esw10gPortSecLimitCtrlPortMode OBJECT-TYPE
   SYNTAX      INTEGER (0|1)
   MAX-ACCESS  read-write
   STATUS      current
   DESCRIPTION
       "default: 0
       0: disable
       1: enable"
   ::= { gel2esw10gPortSecLimitCtrlEntry 2 }

gel2esw10gPortSecLimitCtrlPortLimit OBJECT-TYPE
   SYNTAX      INTEGER(1..1024)
   MAX-ACCESS  read-write
   STATUS      current
   DESCRIPTION
       "default: 4, range: 1-1024"
   ::= { gel2esw10gPortSecLimitCtrlEntry 3 }

gel2esw10gPortSecLimitCtrlPortAction OBJECT-TYPE
   SYNTAX      INTEGER(0..3)
   MAX-ACCESS  read-write
   STATUS      current
   DESCRIPTION
       "default: 0
       0: none
       1: trap
       2: shutdown
       3: trap&shutdown"
   ::= { gel2esw10gPortSecLimitCtrlEntry 4 }

gel2esw10gPortSecLimitCtrlPortState OBJECT-TYPE
   SYNTAX      DisplayString
   MAX-ACCESS  read-only
   STATUS      current
   DESCRIPTION
       ""
   ::= { gel2esw10gPortSecLimitCtrlEntry 5 }

gel2esw10gPortSecLimitCtrlPortReOpen OBJECT-TYPE
   SYNTAX      INTEGER (0|1)
   MAX-ACCESS  read-write
   STATUS      current
   DESCRIPTION
       "default: 0
       0: none
       1: reopen"
   ::= { gel2esw10gPortSecLimitCtrlEntry 6 }

gel2esw10gPortSecSwitchStatusTable OBJECT-TYPE
   SYNTAX      SEQUENCE OF GEL2ESW10GPortSecSwitchStatusEntry
   MAX-ACCESS  not-accessible
   STATUS      current
   DESCRIPTION
       " "
   ::= { gel2esw10gPortSecurity 2 }

gel2esw10gPortSecSwitchStatusEntry OBJECT-TYPE
   SYNTAX      GEL2ESW10GPortSecSwitchStatusEntry
   MAX-ACCESS  not-accessible
   STATUS      current
   DESCRIPTION
       ""
   INDEX    { gel2esw10gPortSecSwitchStatusPort  }
   ::= { gel2esw10gPortSecSwitchStatusTable 1 }

GEL2ESW10GPortSecSwitchStatusEntry ::= SEQUENCE {
   gel2esw10gPortSecSwitchStatusPort                INTEGER,
   gel2esw10gPortSecSwitchStatusUsers               DisplayString,
   gel2esw10gPortSecSwitchStatusState               DisplayString,
   gel2esw10gPortSecSwitchStatusMACCountCurrent     INTEGER,
   gel2esw10gPortSecSwitchStatusMACCountLimit       INTEGER
}

gel2esw10gPortSecSwitchStatusPort OBJECT-TYPE
   SYNTAX      INTEGER (1..4095)
   MAX-ACCESS  not-accessible
   STATUS      current
   DESCRIPTION
       " "
   ::= { gel2esw10gPortSecSwitchStatusEntry 1 }

gel2esw10gPortSecSwitchStatusUsers OBJECT-TYPE
   SYNTAX      DisplayString
   MAX-ACCESS  read-only
   STATUS      current
   DESCRIPTION
       " Users Abbr: L = Limit Control, 8 = 802.1X, D = DHCP Snooping, V = Voice VLAN, 
         '-' means that the corresponding user module is not enabled. "
   ::= { gel2esw10gPortSecSwitchStatusEntry 2 }

gel2esw10gPortSecSwitchStatusState OBJECT-TYPE
   SYNTAX      DisplayString
   MAX-ACCESS  read-only
   STATUS      current
   DESCRIPTION
       " Shows the current state of the port : Disabled, Ready, Limit Reached, Shutdown. "
   ::= { gel2esw10gPortSecSwitchStatusEntry 3 }

gel2esw10gPortSecSwitchStatusMACCountCurrent OBJECT-TYPE
   SYNTAX      INTEGER (1..4095)
   MAX-ACCESS  read-only
   STATUS      current
   DESCRIPTION
       ""
   ::= { gel2esw10gPortSecSwitchStatusEntry 4 }

gel2esw10gPortSecSwitchStatusMACCountLimit OBJECT-TYPE
   SYNTAX      INTEGER(1..4095)
   MAX-ACCESS  read-only
   STATUS      current
   DESCRIPTION
       ""
   ::= { gel2esw10gPortSecSwitchStatusEntry 5 }

gel2esw10gPortSecPortStatus                                      OBJECT IDENTIFIER ::= { gel2esw10gPortSecurity 3 }

gel2esw10gPortSecPortStatusPort OBJECT-TYPE
   SYNTAX       INTEGER (1..4095)
   MAX-ACCESS   read-write
   STATUS       current
   DESCRIPTION
       "default: 0
        0 : None"
   ::= { gel2esw10gPortSecPortStatus 1 }

gel2esw10gPortSecPortStatusTable OBJECT-TYPE
   SYNTAX      SEQUENCE OF GEL2ESW10GPortSecPortStatusEntry
   MAX-ACCESS  not-accessible
   STATUS      current
   DESCRIPTION
      " "
   ::= { gel2esw10gPortSecPortStatus 2 }
       
gel2esw10gPortSecPortStatusEntry OBJECT-TYPE
   SYNTAX      GEL2ESW10GPortSecPortStatusEntry
   MAX-ACCESS  not-accessible
   STATUS      current
   DESCRIPTION
       ""
   INDEX    { gel2esw10gPortSecPortStatusIndex  }
   ::= { gel2esw10gPortSecPortStatusTable 1 }       

GEL2ESW10GPortSecPortStatusEntry ::= SEQUENCE {
   gel2esw10gPortSecPortStatusIndex              INTEGER,
   gel2esw10gPortSecPortStatusMACAddress         MacAddress,
   gel2esw10gPortSecPortStatusVLANId             INTEGER,
   gel2esw10gPortSecPortStatusState              DisplayString,
   gel2esw10gPortSecPortStatusTimeOfAddition     DisplayString,
   gel2esw10gPortSecPortStatusAgeAndHold         DisplayString
}

gel2esw10gPortSecPortStatusIndex OBJECT-TYPE
   SYNTAX      INTEGER(1..4095)
   MAX-ACCESS  not-accessible
   STATUS      current
   DESCRIPTION
       " "
   ::= { gel2esw10gPortSecPortStatusEntry 1 }

gel2esw10gPortSecPortStatusMACAddress OBJECT-TYPE
   SYNTAX      MacAddress
   MAX-ACCESS  read-only
   STATUS      current
   DESCRIPTION
       " "
   ::= { gel2esw10gPortSecPortStatusEntry 2 }

gel2esw10gPortSecPortStatusVLANId OBJECT-TYPE
   SYNTAX      INTEGER(1..4094)
   MAX-ACCESS  read-only
   STATUS      current
   DESCRIPTION
       " "
   ::= { gel2esw10gPortSecPortStatusEntry 3 }

gel2esw10gPortSecPortStatusState OBJECT-TYPE
   SYNTAX      DisplayString
   MAX-ACCESS  read-only
   STATUS      current
   DESCRIPTION
       "Blocked / Forwarding "
   ::= { gel2esw10gPortSecPortStatusEntry 4 }

gel2esw10gPortSecPortStatusTimeOfAddition OBJECT-TYPE
   SYNTAX      DisplayString
   MAX-ACCESS  read-only
   STATUS      current
   DESCRIPTION
       " "
   ::= { gel2esw10gPortSecPortStatusEntry 5 }

gel2esw10gPortSecPortStatusAgeAndHold OBJECT-TYPE
   SYNTAX      DisplayString
   MAX-ACCESS  read-only
   STATUS      current
   DESCRIPTION
       " "
   ::= { gel2esw10gPortSecPortStatusEntry 6 }       
       

gel2esw10gAccessManagement                                      OBJECT IDENTIFIER ::= { gel2esw10gSecurity 6 }

gel2esw10gAccessMgtConf                                         OBJECT IDENTIFIER ::= { gel2esw10gAccessManagement 1 }

gel2esw10gAccessMgtConfMode OBJECT-TYPE
   SYNTAX      INTEGER(0|1)
   MAX-ACCESS  read-write
   STATUS      current
   DESCRIPTION
       "default: 0
       0: disable
       1: enable "
   ::= { gel2esw10gAccessMgtConf 1 }

gel2esw10gAccessMgtConfCreate OBJECT-TYPE
   SYNTAX      INTEGER(0|1)
   MAX-ACCESS  read-write
   STATUS      current
   DESCRIPTION
       "default: 0
       0: none
       1: create "
   ::= { gel2esw10gAccessMgtConf 2 }

gel2esw10gAccessMgtConfTable OBJECT-TYPE
   SYNTAX      SEQUENCE OF GEL2ESW10GAccessMgtConfEntry
   MAX-ACCESS  not-accessible
   STATUS      current
   DESCRIPTION
       " "
   ::= { gel2esw10gAccessMgtConf 3 }

gel2esw10gAccessMgtConfEntry OBJECT-TYPE
   SYNTAX      GEL2ESW10GAccessMgtConfEntry
   MAX-ACCESS  not-accessible
   STATUS      current
   DESCRIPTION
       ""
   INDEX    { gel2esw10gAccessMgtIndex  }
   ::= { gel2esw10gAccessMgtConfTable 1 }
   
GEL2ESW10GAccessMgtConfEntry ::= SEQUENCE {
   gel2esw10gAccessMgtIndex             INTEGER,
   gel2esw10gAccessMgtAddresstype       INTEGER,
   gel2esw10gAccessMgtStartIpAddress    DisplayString,
   gel2esw10gAccessMgtEndIpAddress      DisplayString,
   gel2esw10gAccessMgtHttpHttps         INTEGER,
   gel2esw10gAccessMgtSNMP              INTEGER,
   gel2esw10gAccessMgtTelnetSSH         INTEGER,
   gel2esw10gAccessMgtRowStatus         INTEGER
}

gel2esw10gAccessMgtIndex OBJECT-TYPE
   SYNTAX      INTEGER(1..16)
   MAX-ACCESS  read-write
   STATUS      current
   DESCRIPTION
       "Set Access Management config index
        range : 1-16."
   ::= { gel2esw10gAccessMgtConfEntry 1 }

gel2esw10gAccessMgtAddresstype OBJECT-TYPE
   SYNTAX      INTEGER(0|1)
   MAX-ACCESS  read-write
   STATUS      current
   DESCRIPTION
       "0: ipv4
        1: ipv6 "
   ::= { gel2esw10gAccessMgtConfEntry 2 }
   
gel2esw10gAccessMgtStartIpAddress OBJECT-TYPE
   SYNTAX      DisplayString
   MAX-ACCESS  read-write
   STATUS      current
   DESCRIPTION
       " Start IP address. 
         IP address doesn't allowed all zero or all 'ff'H."
   ::= { gel2esw10gAccessMgtConfEntry 3 }
   
gel2esw10gAccessMgtEndIpAddress OBJECT-TYPE
   SYNTAX      DisplayString
   MAX-ACCESS  read-write
   STATUS      current
   DESCRIPTION
       " End IP address. 
         IP address doesn't allowed all zero or all 'ff'H.
         End ip address is not less than start ip address."
   ::= { gel2esw10gAccessMgtConfEntry 4 }

gel2esw10gAccessMgtHttpHttps OBJECT-TYPE
   SYNTAX      INTEGER(0|1)
   MAX-ACCESS  read-write
   STATUS      current
   DESCRIPTION
       "default: 0
       0: disable
       1: enable "
   ::= { gel2esw10gAccessMgtConfEntry 5 }

gel2esw10gAccessMgtSNMP OBJECT-TYPE
   SYNTAX      INTEGER(0|1)
   MAX-ACCESS  read-write
   STATUS      current
   DESCRIPTION
       "default: 0
       0: disable
       1: enable "
   ::= { gel2esw10gAccessMgtConfEntry 6 }

gel2esw10gAccessMgtTelnetSSH OBJECT-TYPE
   SYNTAX      INTEGER(0|1)
   MAX-ACCESS  read-write
   STATUS      current
   DESCRIPTION
       "default: 0
       0: disable
       1: enable "
   ::= { gel2esw10gAccessMgtConfEntry 7 }

gel2esw10gAccessMgtRowStatus OBJECT-TYPE
   SYNTAX      INTEGER(1..5)
   MAX-ACCESS  read-write
   STATUS      current
   DESCRIPTION
       "1: active
        2: notInservice
        3: edit
        4: destroy
        5: undo"
   ::= { gel2esw10gAccessMgtConfEntry 8 }

gel2esw10gAccessMgtStatistics                                   OBJECT IDENTIFIER ::= { gel2esw10gAccessManagement 2 }

gel2esw10gHttpReceivedPkts OBJECT-TYPE
   SYNTAX      Counter32
   MAX-ACCESS  read-only
   STATUS      current
   DESCRIPTION
       " "
   ::= { gel2esw10gAccessMgtStatistics 1 }

gel2esw10gHttpAllowedPkts OBJECT-TYPE
   SYNTAX      Counter32
   MAX-ACCESS  read-only
   STATUS      current
   DESCRIPTION
       " "
   ::= { gel2esw10gAccessMgtStatistics 2 }

gel2esw10gHttpDiscardedPkts OBJECT-TYPE
   SYNTAX      Counter32
   MAX-ACCESS  read-only
   STATUS      current
   DESCRIPTION
       " "
   ::= { gel2esw10gAccessMgtStatistics 3 }

gel2esw10gHttpsReceivedPkts OBJECT-TYPE
   SYNTAX      Counter32
   MAX-ACCESS  read-only
   STATUS      current
   DESCRIPTION
       " "
   ::= { gel2esw10gAccessMgtStatistics 4 }

gel2esw10gHttpsAllowedPkts OBJECT-TYPE
   SYNTAX      Counter32
   MAX-ACCESS  read-only
   STATUS      current
   DESCRIPTION
       " "
   ::= { gel2esw10gAccessMgtStatistics 5 }

gel2esw10gHttpsDiscardedPkts OBJECT-TYPE
   SYNTAX      Counter32
   MAX-ACCESS  read-only
   STATUS      current
   DESCRIPTION
       " "
   ::= { gel2esw10gAccessMgtStatistics 6 }

gel2esw10gSnmpReceivedPkts OBJECT-TYPE
   SYNTAX      Counter32
   MAX-ACCESS  read-only
   STATUS      current
   DESCRIPTION
       " "
   ::= { gel2esw10gAccessMgtStatistics 7 }

gel2esw10gSnmpAllowedPkts OBJECT-TYPE
   SYNTAX      Counter32
   MAX-ACCESS  read-only
   STATUS      current
   DESCRIPTION
       " "
   ::= { gel2esw10gAccessMgtStatistics 8 }

gel2esw10gSnmpDiscardedPkts OBJECT-TYPE
   SYNTAX      Counter32
   MAX-ACCESS  read-only
   STATUS      current
   DESCRIPTION
       " "
   ::= { gel2esw10gAccessMgtStatistics 9 }

gel2esw10gTelnetReceivedPkts OBJECT-TYPE
   SYNTAX      Counter32
   MAX-ACCESS  read-only
   STATUS      current
   DESCRIPTION
       " "
   ::= { gel2esw10gAccessMgtStatistics 10 }

gel2esw10gTelnetAllowedPkts OBJECT-TYPE
   SYNTAX      Counter32
   MAX-ACCESS  read-only
   STATUS      current
   DESCRIPTION
       " "
   ::= { gel2esw10gAccessMgtStatistics 11 }

gel2esw10gTelnetDiscardedPkts OBJECT-TYPE
   SYNTAX      Counter32
   MAX-ACCESS  read-only
   STATUS      current
   DESCRIPTION
       " "
   ::= { gel2esw10gAccessMgtStatistics 12 }

gel2esw10gSSHReceivedPkts OBJECT-TYPE
   SYNTAX      Counter32
   MAX-ACCESS  read-only
   STATUS      current
   DESCRIPTION
       " "
   ::= { gel2esw10gAccessMgtStatistics 13 }

gel2esw10gSSHAllowedPkts OBJECT-TYPE
   SYNTAX      Counter32
   MAX-ACCESS  read-only
   STATUS      current
   DESCRIPTION
       " "
   ::= { gel2esw10gAccessMgtStatistics 14 }

gel2esw10gSSHDiscardedPkts OBJECT-TYPE
   SYNTAX      Counter32
   MAX-ACCESS  read-only
   STATUS      current
   DESCRIPTION
       " "
   ::= { gel2esw10gAccessMgtStatistics 15 }

gel2esw10gAccessMgtStatisticsClearAll OBJECT-TYPE
   SYNTAX      INTEGER(0|1)
   MAX-ACCESS  read-write
   STATUS      current
   DESCRIPTION
       "0: none
        1: clear"
   ::= { gel2esw10gAccessMgtStatistics 16 }

gel2esw10gSSH                                                   OBJECT IDENTIFIER ::= { gel2esw10gSecurity 7 }

gel2esw10gSSHMode OBJECT-TYPE
   SYNTAX      INTEGER(0|1)
   MAX-ACCESS  read-write
   STATUS      current
   DESCRIPTION
       "default: 1
        0: disable
        1: enable"
   ::= { gel2esw10gSSH 1 }

gel2esw10gHTTPS                                                 OBJECT IDENTIFIER ::= { gel2esw10gSecurity 8 }

gel2esw10gHTTPSMode OBJECT-TYPE
   SYNTAX      INTEGER(0|1)
   MAX-ACCESS  read-write
   STATUS      current
   DESCRIPTION
       "default: 1
        0: disable
        1: enable"
   ::= { gel2esw10gHTTPS 1 }

gel2esw10gHTTPSAutoRedirect OBJECT-TYPE
   SYNTAX      INTEGER(0|1)
   MAX-ACCESS  read-write
   STATUS      current
   DESCRIPTION
       "default: 0
        0: disable
        1: enable"
   ::= { gel2esw10gHTTPS 2 }

gel2esw10gAuthMethod                                            OBJECT IDENTIFIER ::= { gel2esw10gSecurity 9 }

gel2esw10gConsoleAuthMethod OBJECT-TYPE
   SYNTAX      INTEGER(0..3)
   MAX-ACCESS  read-write
   STATUS      current
   DESCRIPTION
       "default: 1
        0: none
        1: local
        2: RADIUS
        3: TACACS+"
   ::= { gel2esw10gAuthMethod 1 }

gel2esw10gConsoleFallback OBJECT-TYPE
   SYNTAX      INTEGER(0|1)
   MAX-ACCESS  read-write
   STATUS      current
   DESCRIPTION
       "default: 0
        0:disable
        1:enable"
   ::= { gel2esw10gAuthMethod 2 }

gel2esw10gTelnetAuthMethod OBJECT-TYPE
   SYNTAX      INTEGER(0..3)
   MAX-ACCESS  read-write
   STATUS      current
   DESCRIPTION
       "default: 1
        0: none
        1: local
        2: RADIUS
        3: TACACS+"
   ::= { gel2esw10gAuthMethod 3 }

gel2esw10gTelnetFallback OBJECT-TYPE
   SYNTAX      INTEGER(0|1)
   MAX-ACCESS  read-write
   STATUS      current
   DESCRIPTION
       "default: 0
        0:disable
        1:enable"
   ::= { gel2esw10gAuthMethod 4 }

gel2esw10gSshAuthMethod OBJECT-TYPE
   SYNTAX      INTEGER(0..3)
   MAX-ACCESS  read-write
   STATUS      current
   DESCRIPTION
       "default: 1
        0: none
        1: local
        2: RADIUS
        3: TACACS+"
   ::= { gel2esw10gAuthMethod 5 }

gel2esw10gSshFallback OBJECT-TYPE
   SYNTAX      INTEGER(0|1)
   MAX-ACCESS  read-write
   STATUS      current
   DESCRIPTION
       "default: 0
        0:disable
        1:enable"
   ::= { gel2esw10gAuthMethod 6 }

gel2esw10gWebAuthMethod OBJECT-TYPE
   SYNTAX      INTEGER(0..3)
   MAX-ACCESS  read-write
   STATUS      current
   DESCRIPTION
       "default: 1
        0: none
        1: local
        2: RADIUS
        3: TACACS+"
   ::= { gel2esw10gAuthMethod 7 }

gel2esw10gWebFallback OBJECT-TYPE
   SYNTAX      INTEGER(0|1)
   MAX-ACCESS  read-write
   STATUS      current
   DESCRIPTION
       "default: 0
        0:disable
        1:enable"
   ::= { gel2esw10gAuthMethod 8 }

gel2esw10gMaintenance                                           OBJECT IDENTIFIER ::= { gel2esw10gProductId 4 }

gel2esw10gRestartDevice OBJECT-TYPE
   SYNTAX      INTEGER(0|1)
   MAX-ACCESS  read-write
   STATUS      current
   DESCRIPTION
       "default: 0
        0:none
        1:yes"
   ::= { gel2esw10gMaintenance 1 }

gel2esw10gFirmware                                         OBJECT IDENTIFIER ::= { gel2esw10gMaintenance 2 }

gel2esw10gFirmwareIpAddress OBJECT-TYPE
   SYNTAX       IpAddress
   MAX-ACCESS   read-write
   STATUS       current
   DESCRIPTION
        "Get/Set the firmware tftp server."
   ::= { gel2esw10gFirmware 1 }

gel2esw10gFirmwareFileName OBJECT-TYPE
   SYNTAX       DisplayString
   MAX-ACCESS   read-write
   STATUS       current
   DESCRIPTION
        "Get/Set the path and filename for firmware upgrading."
   ::= { gel2esw10gFirmware 2 }

gel2esw10gDoFirmwareUpgrade OBJECT-TYPE
   SYNTAX       INTEGER(0|1)
   MAX-ACCESS   read-write
   STATUS       current
   DESCRIPTION
        "Do firmware upgrade. Get this OID always return zero.
              1 - do firmware upgrade.
              0 - do nothing."
   ::= { gel2esw10gFirmware 3 }

gel2esw10gSaveOrRestore                                         OBJECT IDENTIFIER ::= { gel2esw10gMaintenance 3 }

gel2esw10gFactoryDefaults OBJECT-TYPE
   SYNTAX      INTEGER(0|1)
   MAX-ACCESS  read-write
   STATUS      current
   DESCRIPTION
       "default: 0
        0:none
        1:yes"
   ::= { gel2esw10gSaveOrRestore 1 }

gel2esw10gSaveStart OBJECT-TYPE
   SYNTAX      INTEGER(0|1)
   MAX-ACCESS  read-write
   STATUS      current
   DESCRIPTION
       "default: 0
        0:none
        1:yes"
   ::= { gel2esw10gSaveOrRestore 2 }

gel2esw10gSaveUser OBJECT-TYPE
   SYNTAX      INTEGER(0|1)
   MAX-ACCESS  read-write
   STATUS      current
   DESCRIPTION
       "default: 0
        0:none
        1:yes"
   ::= { gel2esw10gSaveOrRestore 3 }

gel2esw10gRestoreUser OBJECT-TYPE
   SYNTAX      INTEGER(0|1)
   MAX-ACCESS  read-write
   STATUS      current
   DESCRIPTION
       "default: 0
        0:none
        1:yes"
   ::= { gel2esw10gSaveOrRestore 4 }


gel2esw10gExportOrImport                                        OBJECT IDENTIFIER ::= { gel2esw10gMaintenance 4 }

gel2esw10gExportIpAddress OBJECT-TYPE
   SYNTAX       IpAddress
   MAX-ACCESS   read-write
   STATUS       current
   DESCRIPTION
        "Get/Set the export tftp server."
   ::= { gel2esw10gExportOrImport 1 }

gel2esw10gExportConfigName OBJECT-TYPE
   SYNTAX       DisplayString
   MAX-ACCESS   read-write
   STATUS       current
   DESCRIPTION
       "Get/Set the export file path and name."
   ::= { gel2esw10gExportOrImport 2 }

gel2esw10gDoExportConfig OBJECT-TYPE
   SYNTAX       INTEGER(1)
   MAX-ACCESS   read-write
   STATUS       current
   DESCRIPTION
        "Do export-config.
         Get this OID always return zero.
         1 - export."
   ::= { gel2esw10gExportOrImport 3 }

gel2esw10gImportIpAddress OBJECT-TYPE
   SYNTAX       IpAddress
   MAX-ACCESS   read-write
   STATUS       current
   DESCRIPTION
        "Get/Set the import tftp server."
   ::= { gel2esw10gExportOrImport 4 }

gel2esw10gImportConfigName OBJECT-TYPE
   SYNTAX      DisplayString
   MAX-ACCESS  read-write
   STATUS      current
   DESCRIPTION
       "Get/Set the import file path and name."
   ::= { gel2esw10gExportOrImport 5 }

gel2esw10gDoImportConfig OBJECT-TYPE
   SYNTAX       INTEGER(1)
   MAX-ACCESS   read-write
   STATUS       current
   DESCRIPTION
        "Do export-config.
         Get this OID always return zero.
         1 - import."
   ::= { gel2esw10gExportOrImport 6 }

gel2esw10gDiagnostics                                           OBJECT IDENTIFIER ::= { gel2esw10gMaintenance 5 }

gel2esw10gPingIpAddress OBJECT-TYPE
   SYNTAX      IpAddress
   MAX-ACCESS  read-write
   STATUS      current
   DESCRIPTION
       " The destination IP Address. "
   ::= { gel2esw10gDiagnostics 1 }
   
gel2esw10gPingSize OBJECT-TYPE
   SYNTAX      INTEGER(60..1400)
   MAX-ACCESS  read-write
   STATUS      current
   DESCRIPTION
       " Size of ICMP echo packet.
         range : 60-1400, default : 64. "
   ::= { gel2esw10gDiagnostics 2 }   

gel2esw10gDoPingConfig OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gel2esw10gDiagnostics 3 }

gel2esw10gPingResult OBJECT-TYPE
   SYNTAX      DisplayString
   MAX-ACCESS  read-only
   STATUS      current
   DESCRIPTION
       " Show ping result. "
   ::= { gel2esw10gDiagnostics 4 }

gel2esw10gPing6IpAddress OBJECT-TYPE
   SYNTAX      DisplayString
   MAX-ACCESS  read-write
   STATUS      current
   DESCRIPTION
       " The destination IPv6 Address. "
   ::= { gel2esw10gDiagnostics 5 }
   
gel2esw10gPing6Size OBJECT-TYPE
   SYNTAX      INTEGER(60..1400)
   MAX-ACCESS  read-write
   STATUS      current
   DESCRIPTION
       " Size of ICMP echo packet.
         range : 60-1400. "
   ::= { gel2esw10gDiagnostics 6 }   

gel2esw10gDoPing6Config OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gel2esw10gDiagnostics 7 }

gel2esw10gPing6Result OBJECT-TYPE
   SYNTAX      DisplayString
   MAX-ACCESS  read-only
   STATUS      current
   DESCRIPTION
       " Show ping result. "
   ::= { gel2esw10gDiagnostics 8 }


gel2esw10gVeriPHY                                           OBJECT IDENTIFIER ::= { gel2esw10gDiagnostics 9 }

gel2esw10gVeriPHYTest OBJECT-TYPE
   SYNTAX      INTEGER (1..4095)
   MAX-ACCESS  read-write
   STATUS      current
   DESCRIPTION
       "Run VeriPHY Cable Diagnostics.
        port, range : 0 - port number.
        0 : ALL "
   ::= { gel2esw10gVeriPHY 1 }

gel2esw10gVeriPHYTable OBJECT-TYPE
   SYNTAX      SEQUENCE OF GEL2ESW10GVeriPHYEntry
   MAX-ACCESS  not-accessible
   STATUS      current
   DESCRIPTION
       " "
   ::= { gel2esw10gVeriPHY 2 }

gel2esw10gVeriPHYEntry OBJECT-TYPE
   SYNTAX      GEL2ESW10GVeriPHYEntry
   MAX-ACCESS  not-accessible
   STATUS      current
   DESCRIPTION
       ""
   INDEX    { gel2esw10gVeriPHYPort  }
   ::= { gel2esw10gVeriPHYTable 1 }

GEL2ESW10GVeriPHYEntry ::= SEQUENCE {
   gel2esw10gVeriPHYPort        INTEGER,
   gel2esw10gVeriPHYPairA       DisplayString,
   gel2esw10gVeriPHYLengthA     DisplayString,
   gel2esw10gVeriPHYPairB       DisplayString,
   gel2esw10gVeriPHYLengthB     DisplayString,
   gel2esw10gVeriPHYPairC       DisplayString,
   gel2esw10gVeriPHYLengthC     DisplayString,
   gel2esw10gVeriPHYPairD       DisplayString,
   gel2esw10gVeriPHYLengthD     DisplayString
}

gel2esw10gVeriPHYPort OBJECT-TYPE
   SYNTAX      INTEGER (1..4095)
   MAX-ACCESS  not-accessible
   STATUS      current
   DESCRIPTION
       " The length (in meters) of the cable pair. "
   ::= { gel2esw10gVeriPHYEntry 1 }

gel2esw10gVeriPHYPairA OBJECT-TYPE
   SYNTAX      DisplayString
   MAX-ACCESS  read-only
   STATUS      current
   DESCRIPTION
       " The status of the cable pair. "
   ::= { gel2esw10gVeriPHYEntry 2 }

gel2esw10gVeriPHYLengthA OBJECT-TYPE
   SYNTAX      DisplayString
   MAX-ACCESS  read-only
   STATUS      current
   DESCRIPTION
       " The length (in meters) of the cable pair. "
   ::= { gel2esw10gVeriPHYEntry 3 }

gel2esw10gVeriPHYPairB OBJECT-TYPE
   SYNTAX      DisplayString
   MAX-ACCESS  read-only
   STATUS      current
   DESCRIPTION
       " The status of the cable pair. "
   ::= { gel2esw10gVeriPHYEntry 4 }

gel2esw10gVeriPHYLengthB OBJECT-TYPE
   SYNTAX      DisplayString
   MAX-ACCESS  read-only
   STATUS      current
   DESCRIPTION
       " The length (in meters) of the cable pair. "
   ::= { gel2esw10gVeriPHYEntry 5 }

gel2esw10gVeriPHYPairC OBJECT-TYPE
   SYNTAX      DisplayString
   MAX-ACCESS  read-only
   STATUS      current
   DESCRIPTION
       " The status of the cable pair. "
   ::= { gel2esw10gVeriPHYEntry 6 }

gel2esw10gVeriPHYLengthC OBJECT-TYPE
   SYNTAX      DisplayString
   MAX-ACCESS  read-only
   STATUS      current
   DESCRIPTION
       " The length (in meters) of the cable pair. "
   ::= { gel2esw10gVeriPHYEntry 7 }

gel2esw10gVeriPHYPairD OBJECT-TYPE
   SYNTAX      DisplayString
   MAX-ACCESS  read-only
   STATUS      current
   DESCRIPTION
       " The status of the cable pair. "
   ::= { gel2esw10gVeriPHYEntry 8 }

gel2esw10gVeriPHYLengthD OBJECT-TYPE
   SYNTAX      DisplayString
   MAX-ACCESS  read-only
   STATUS      current
   DESCRIPTION
       " The length (in meters) of the cable pair. "
   ::= { gel2esw10gVeriPHYEntry 9 }


------------------------------------------------------------------------------------------------------------------
gel2esw10gTrap                                                  OBJECT IDENTIFIER ::= { gel2esw10gProductId 5 }

gel2esw10gTrapEvent                                             OBJECT IDENTIFIER ::= { gel2esw10gTrap 1 }

gel2esw10gEmergency NOTIFICATION-TYPE
  OBJECTS   { gel2esw10gInformation }
  STATUS        current
    DESCRIPTION
        "The severity level is Emergency. The system is unusable."
    ::= { gel2esw10gTrapEvent 1 }

gel2esw10gAlert NOTIFICATION-TYPE
  OBJECTS   { gel2esw10gInformation }
  STATUS        current
    DESCRIPTION
        "The severity level is Alert. The action must be taken immediately."
    ::= { gel2esw10gTrapEvent 2 }

gel2esw10gCritical NOTIFICATION-TYPE
  OBJECTS   { gel2esw10gInformation }
  STATUS        current
    DESCRIPTION
        "The severity level is Critical. Critical conditions."
    ::= { gel2esw10gTrapEvent 3 }

gel2esw10gError NOTIFICATION-TYPE
  OBJECTS   { gel2esw10gInformation }
  STATUS        current
    DESCRIPTION
        "The severity level is Error. Error conditions."
    ::= { gel2esw10gTrapEvent 4 }

gel2esw10gWarning NOTIFICATION-TYPE
  OBJECTS   { gel2esw10gInformation }
  STATUS        current
    DESCRIPTION
        "The severity level is Warning. Warning conditions."
    ::= { gel2esw10gTrapEvent 5 }

gel2esw10gNotice NOTIFICATION-TYPE
  OBJECTS   { gel2esw10gInformation }
  STATUS        current
    DESCRIPTION
        "The severity level is Notice. Normal but significant condition."
    ::= { gel2esw10gTrapEvent 6 }

gel2esw10gInformational NOTIFICATION-TYPE
  OBJECTS   { gel2esw10gInformation }
  STATUS        current
    DESCRIPTION
        "The severity level is Informational. Informational messages."
    ::= { gel2esw10gTrapEvent 7 }

gel2esw10gDebug NOTIFICATION-TYPE
  OBJECTS   { gel2esw10gInformation }
  STATUS        current
    DESCRIPTION
        "The severity level is Debug. debug-level messages."
    ::= { gel2esw10gTrapEvent 8 }

gel2esw10gTrapVariable                                          OBJECT IDENTIFIER ::= { gel2esw10gTrap 2 }

gel2esw10gInformation OBJECT-TYPE
    SYNTAX      DisplayString
    MAX-ACCESS  read-only
    STATUS      current
    DESCRIPTION
        "Trap information."
    ::= { gel2esw10gTrapVariable 1 }


END
