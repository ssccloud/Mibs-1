APENT-MIB DEFINITIONS ::= BEGIN

    IMPORTS
            MODULE-IDENTITY 
                FROM SNMPv2-SMI
            enterprises
                FROM RFC1155-SMI;

  arrowPoint OBJECT IDENTIFIER ::= { enterprises 2467 }
--        arrowPoint MODULE-IDENTITY
--           LAST-UPDATED "9707202000Z"    Wed July 20 20:00:00 EST 1997
--           ORGANIZATION "ArrowPoint Communications Inc."
--           CONTACT-INFO
--           "                      Steven Colby
--           Postal:               ArrowPoint Communications Inc.
--				                 50 Nagog Park
--				                 Acton, Massachusetts 01720
--	   Tel:                   +1 978-206-3000  option 1
--	   E-Mail:                support@arrowpoint.com"
--       DESCRIPTION
--          "The MIB module used to describe the ArrowPoint Communications
--          Enterprise MIB branch."
--      ::= { enterprises 2467 }

apMgmt          OBJECT IDENTIFIER ::= {arrowPoint 1}
apLocal         OBJECT IDENTIFIER ::= {arrowPoint 2}
apTemp          OBJECT IDENTIFIER ::= {arrowPoint 3}
apProducts      OBJECT IDENTIFIER ::= {arrowPoint 4}
apCS100         OBJECT IDENTIFIER ::= {apProducts 1}
apCS800         OBJECT IDENTIFIER ::= {apProducts 2}
apCS150         OBJECT IDENTIFIER ::= {apProducts 3}
apCS50          OBJECT IDENTIFIER ::= {apProducts 4}
pppExt          OBJECT IDENTIFIER ::= {apMgmt 1}
frExt           OBJECT IDENTIFIER ::= {apMgmt 2}
isdnExt         OBJECT IDENTIFIER ::= {apMgmt 3}
firewall        OBJECT IDENTIFIER ::= {apMgmt 4}
qos             OBJECT IDENTIFIER ::= {apMgmt 5}
localBalance    OBJECT IDENTIFIER ::= {apMgmt 6}
remoteBalance   OBJECT IDENTIFIER ::= {apMgmt 7}
tunnelExt       OBJECT IDENTIFIER ::= {apMgmt 8}
ipv4Ext         OBJECT IDENTIFIER ::= {apMgmt 9}
  apIpv4                    OBJECT IDENTIFIER ::= {ipv4Ext 1}
  apIpv4Interface           OBJECT IDENTIFIER ::= {ipv4Ext 2}
  apIpv4RoutingProtocols    OBJECT IDENTIFIER ::= {ipv4Ext 3}
    apIpv4Rip                 OBJECT IDENTIFIER ::= {apIpv4RoutingProtocols 1}
    apIpv4Ospf                OBJECT IDENTIFIER ::= {apIpv4RoutingProtocols 2}
  apIpv4Arp                 OBJECT IDENTIFIER ::= {ipv4Ext 4}
  apIpv4StaticRoutes        OBJECT IDENTIFIER ::= {ipv4Ext 5}
  apIpv4Host                OBJECT IDENTIFIER ::= {ipv4Ext 6}
  apIpv4Dns                 OBJECT IDENTIFIER ::= {ipv4Ext 7}
  apIpv4Redundancy          OBJECT IDENTIFIER ::= {ipv4Ext 8}
connMgmt        OBJECT IDENTIFIER ::= {apMgmt 10}
terminalMgmt    OBJECT IDENTIFIER ::= {apMgmt 11}
radiusClientExt OBJECT IDENTIFIER ::= {apMgmt 12}
securityMgrExt  OBJECT IDENTIFIER ::= {apMgmt 13}
bridgeExt       OBJECT IDENTIFIER ::= {apMgmt 14}
svcExt          OBJECT IDENTIFIER ::= {apMgmt 15}
cntExt          OBJECT IDENTIFIER ::= {apMgmt 16}
grpExt          OBJECT IDENTIFIER ::= {apMgmt 17}
cntsvcExt       OBJECT IDENTIFIER ::= {apMgmt 18}
grpsvcExt       OBJECT IDENTIFIER ::= {apMgmt 19}
logExt          OBJECT IDENTIFIER ::= {apMgmt 20}
ds1Ext          OBJECT IDENTIFIER ::= {apMgmt 21}
snmpExt         OBJECT IDENTIFIER ::= {apMgmt 22}
aclExt          OBJECT IDENTIFIER ::= {apMgmt 23}
ifExt           OBJECT IDENTIFIER ::= {apMgmt 24}
ownExt          OBJECT IDENTIFIER ::= {apMgmt 25}
bwdthExt        OBJECT IDENTIFIER ::= {apMgmt 26}
ispgrpExt       OBJECT IDENTIFIER ::= {apMgmt 27}
qosExt          OBJECT IDENTIFIER ::= {apMgmt 28}
cctExt          OBJECT IDENTIFIER ::= {apMgmt 29}
ftpExt          OBJECT IDENTIFIER ::= {apMgmt 30}
bootExt         OBJECT IDENTIFIER ::= {apMgmt 31}
appExt          OBJECT IDENTIFIER ::= {apMgmt 32}
hssiExt         OBJECT IDENTIFIER ::= {apMgmt 33}
chassisMgrExt   OBJECT IDENTIFIER ::= {apMgmt 34}
cnthotExt       OBJECT IDENTIFIER ::= {apMgmt 35}
flowMgrExt      OBJECT IDENTIFIER ::= {apMgmt 36}
webMgmtExt      OBJECT IDENTIFIER ::= {apMgmt 37}
csrpExt         OBJECT IDENTIFIER ::= {apMgmt 38}
enetExt         OBJECT IDENTIFIER ::= {apMgmt 39}
dnsServerExt    OBJECT IDENTIFIER ::= {apMgmt 40}
cntdnsExt       OBJECT IDENTIFIER ::= {apMgmt 41}
eqlExt          OBJECT IDENTIFIER ::= {apMgmt 42}
sshdExt         OBJECT IDENTIFIER ::= {apMgmt 43}
ap64Stats       OBJECT IDENTIFIER ::= {apMgmt 44}
schedExt        OBJECT IDENTIFIER ::= {apMgmt 45}
kalExt          OBJECT IDENTIFIER ::= {apMgmt 46}
httpExt         OBJECT IDENTIFIER ::= {apMgmt 47}
dnshotExt       OBJECT IDENTIFIER ::= {apMgmt 48}
urqlExt         OBJECT IDENTIFIER ::= {apMgmt 49}
nqlExt          OBJECT IDENTIFIER ::= {apMgmt 50}
dqlExt          OBJECT IDENTIFIER ::= {apMgmt 51}
cappUdpExt      OBJECT IDENTIFIER ::= {apMgmt 52}
tagExt          OBJECT IDENTIFIER ::= {apMgmt 53}
proxDbExt       OBJECT IDENTIFIER ::= {apMgmt 54}
probeRttExt     OBJECT IDENTIFIER ::= {apMgmt 55}
plucExt         OBJECT IDENTIFIER ::= {apMgmt 56}  
publishExt		OBJECT IDENTIFIER ::= {apMgmt 57} 
subscribeExt	OBJECT IDENTIFIER ::= {apMgmt 58}
chassis         OBJECT IDENTIFIER ::= {apLocal 1}
flash           OBJECT IDENTIFIER ::= {apLocal 2}
layerDepend     OBJECT IDENTIFIER ::= {apTemp  1}

END
