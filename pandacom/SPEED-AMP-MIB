SPEED-AMP-MIB DEFINITIONS ::= BEGIN

--*****************************************************************************************
--*****   Version History   ***************************************************************
--=========================================================================================

--V0.0  14.04.2009 GD: Erste Version SPEED-AMP-MIB
--V1.0  18.06.2009 GD: ueberarbeitete Version Als Referenz für Implementierung in SNMP
--V1.1  25.08.2009 GD: Alias Werte hinzugefügt, Umrechnungswerte für ananloge Parameter ergaenzt
--  Supported Modules:
--                             SPEED-AMPLIFIER
--*****************************************************************************************

IMPORTS
	DisplayString	FROM RFC1213-MIB
	OBJECT-TYPE	FROM RFC-1212
	TRAP-TYPE	FROM RFC-1215
	enterprises, IpAddress, TimeTicks, MODULE-IDENTITY	FROM SNMPv2-SMI
	PanDacom	FROM PanDacom-MIB
	nmSPEEDCARRIER, amplifier	FROM SPEEDCARRIER-MIB
; -- END of IMPORTS

--*******************************************************************

	speedAmp MODULE-IDENTITY
		LAST-UPDATED "0908251730Z"
		ORGANIZATION "Pan Dacom Direkt GmbH"
		CONTACT-INFO
			"Pan Dacom Direkt GmbH
			Dreieich Plaza 1B
			63303 Dreieich
			Germany
			Tel. : +49 6103/932-333
			Fax. : +49 6103/932-444
			email: kontakt@pandacomdirekt.de
			web  : www.pandacomdirekt.de"
		DESCRIPTION "Revision 1.0"
		::= { amplifier 1 }

--*******************************************************************

	speedAmpModuleOverviewTable OBJECT-TYPE
		SYNTAX SEQUENCE OF SpeedAmpModuleOverviewEntry
		MAX-ACCESS not-accessible
		STATUS current
		DESCRIPTION
			"Speed-Amplifier Module Overview Table"
		::= { speedAmp 1 }

	speedAmpModuleOverviewEntry OBJECT-TYPE
		SYNTAX SpeedAmpModuleOverviewEntry
		MAX-ACCESS not-accessible
		STATUS current
		DESCRIPTION
			"Module Overview Entries"
		INDEX { speedAmpIndex }
		::= { speedAmpModuleOverviewTable 1 }

	SpeedAmpModuleOverviewEntry ::=
		SEQUENCE
		{
			speedAmpIndex INTEGER,
			speedAmpMSlot INTEGER,
			speedAmpMDevice INTEGER,
			speedAmpMStatus INTEGER,
			speedAmpMSysUpTime TimeTicks,
			speedAmpMTemp INTEGER,
			speedAmpMAlarmState INTEGER,
			speedAmpMSerialNumber DisplayString
		}

	speedAmpIndex OBJECT-TYPE
		SYNTAX INTEGER
		MAX-ACCESS  read-only
		STATUS  current
		DESCRIPTION  "SPEED AMP Module Index"
		::= { speedAmpModuleOverviewEntry 1 }

	speedAmpMSlot OBJECT-TYPE
		SYNTAX INTEGER (1..17)
		MAX-ACCESS  read-only
		STATUS  current
		DESCRIPTION  "Slot number in Carrier"
		::= { speedAmpModuleOverviewEntry 2 }

	speedAmpMDevice OBJECT-TYPE
		SYNTAX INTEGER
		{
			notAvailable (0),
			other(1),
			preamp14(2),
			booster17(3),
			booster17-OSC(4),
			booster23-OSC(5),
			inline17(6),
			inline23(7),
			Unknown (255)
		}
		MAX-ACCESS  read-only
		STATUS  current
		DESCRIPTION  "Module DeviceType"
		::= { speedAmpModuleOverviewEntry 3 }

	speedAmpMStatus OBJECT-TYPE
		SYNTAX INTEGER
		{
			notAvailable (0),
			running (1),
			resetSoftware (2),
			resetConfig (3),
			resetCAN (4),
			resetHardware (5),
			resetStatistic(6),
			unknown (255)
		}
		MAX-ACCESS  read-write
		STATUS  current
		DESCRIPTION  "Reset States of Module"
		::= { speedAmpModuleOverviewEntry 4 }

	speedAmpMSysUpTime OBJECT-TYPE
		SYNTAX TimeTicks
		MAX-ACCESS  read-only
		STATUS  current
		DESCRIPTION
				"System Up Time in Seconds"
		::= { speedAmpModuleOverviewEntry 5 }

	speedAmpMTemp OBJECT-TYPE
		SYNTAX INTEGER
		MAX-ACCESS  read-only
		STATUS  current
		DESCRIPTION
				"Module Temperature"
		::= { speedAmpModuleOverviewEntry 6 }

	speedAmpMAlarmState OBJECT-TYPE
		SYNTAX INTEGER
		{
			notAvailable (0),
			noAlarm (1),
			activeAlarms (2),
			unknown (255)
		}
		MAX-ACCESS  read-only
		STATUS  current
		DESCRIPTION
				"Module Alarm States, if there are active see Event-Table"
		::= { speedAmpModuleOverviewEntry 7 }

	speedAmpMSerialNumber OBJECT-TYPE
		SYNTAX DisplayString (SIZE (0..17))
		MAX-ACCESS  read-only
		STATUS  current
		DESCRIPTION
				"Modules Serial Number"
		::= { speedAmpModuleOverviewEntry 8 }

-- *********************************
-- speedAmpModuleImagesOverview

	speedAmpModuleImagesOverviewTable OBJECT-TYPE
		SYNTAX SEQUENCE OF SpeedAmpModuleImagesOverviewEntry
		MAX-ACCESS not-accessible
		STATUS current
		DESCRIPTION
				"SPEED-AMPLIFIER Module Images Table"
		::= { speedAmp 2 }

	speedAmpModuleImagesOverviewEntry OBJECT-TYPE
		SYNTAX SpeedAmpModuleImagesOverviewEntry
		MAX-ACCESS not-accessible
		STATUS current
		DESCRIPTION
				"Module Images Overview Entries"
		INDEX { speedAmpIndex }
		::= { speedAmpModuleImagesOverviewTable 1 }

	SpeedAmpModuleImagesOverviewEntry ::=
		SEQUENCE
		{
			speedAmpMSlot			INTEGER,
			speedAmpSwKernelImage		DisplayString,
			speedAmpSwAppImage		DisplayString,
			speedAmpSwUploadStatus		INTEGER,
			speedAmpSwUpdateStatus		INTEGER,
			speedAmpHwVersion		DisplayString
		}

	speedAmpSwKernelImage OBJECT-TYPE
		SYNTAX DisplayString (SIZE (0..32))
		MAX-ACCESS  read-only
		STATUS  current
		DESCRIPTION
				"Identification of Bootimage"
		::= { speedAmpModuleImagesOverviewEntry 3 }

	speedAmpSwAppImage OBJECT-TYPE
		SYNTAX DisplayString (SIZE (0..32))
		MAX-ACCESS  read-only
		STATUS  current
		DESCRIPTION
				"Identification of Application Image1"
		::= { speedAmpModuleImagesOverviewEntry 4 }

	speedAmpSwUploadStatus OBJECT-TYPE
		SYNTAX INTEGER
		{
			notAvailable (0),
			ready (1),
			startUpload (2),
			uploadActive (3),
			uploadFailure (4),
			unknown (255)
		}
		MAX-ACCESS  read-only
		STATUS  current
		DESCRIPTION
			"Control and Status of UploadProcedure"
		::= { speedAmpModuleImagesOverviewEntry 5 }


	speedAmpSwUpdateStatus OBJECT-TYPE
		SYNTAX INTEGER
		{
			notAvailable (0),
			idle (1),
			activateKernel (2),
			activateApplication (3),
			unknown (255)
		}
		MAX-ACCESS  read-only
		STATUS  current
		DESCRIPTION
				"activates SW-Image after netxt reset"
		::= { speedAmpModuleImagesOverviewEntry 6 }

	speedAmpHwVersion OBJECT-TYPE
		SYNTAX DisplayString (SIZE (0..17))
		MAX-ACCESS  read-only
		STATUS  current
		DESCRIPTION
				"Identification of Hardware Version"
		::= { speedAmpModuleImagesOverviewEntry 7 }

-- *********************************
-- SpeedAmpModuleBoardConfig

	speedAmpModuleBoardConfigTable OBJECT-TYPE
		SYNTAX SEQUENCE OF SpeedAmpModuleBoardConfigEntry
		MAX-ACCESS not-accessible
		STATUS current
		DESCRIPTION
			"SPEED-AMPLIFIER Module config Table"
		::= { speedAmp 3 }

	speedAmpModuleBoardConfigEntry OBJECT-TYPE
		SYNTAX SpeedAmpModuleBoardConfigEntry
		MAX-ACCESS not-accessible
		STATUS current
		DESCRIPTION
			"Module Overview Entries"
		INDEX { speedAmpIndex }
		::= { speedAmpModuleBoardConfigTable 1 }

	SpeedAmpModuleBoardConfigEntry ::=
		SEQUENCE
		{
			speedAmpMSlot INTEGER,
			speedAmpTemperatureHighWarning INTEGER,
			speedAmpTemperatureHighAlarm INTEGER
		}

	speedAmpTemperatureHighWarning OBJECT-TYPE
		SYNTAX	INTEGER(5..60)
		MAX-ACCESS	read-write
		STATUS	current
		DESCRIPTION
			"Warning Level for Module ambient Temperature (5 - 60 degree Celsius)"
		::= { speedAmpModuleBoardConfigEntry 3 }

	speedAmpTemperatureHighAlarm OBJECT-TYPE
		SYNTAX	INTEGER
		MAX-ACCESS	read-only
		STATUS	current
		DESCRIPTION
			"Alarm Level for Module ambient Temperature"
		::= { speedAmpModuleBoardConfigEntry 4 }

-- ****************************

	speedAmpModuleNetworkParameterTable OBJECT-TYPE
		SYNTAX SEQUENCE OF SpeedAmpModuleNetworkParameterEntry
		MAX-ACCESS not-accessible
		STATUS current
		DESCRIPTION
				"SPEED-AMPLIFIER Module Network Parameter Table"
		::= { speedAmp 4 }

	speedAmpModuleNetworkParameterEntry OBJECT-TYPE
		SYNTAX SpeedAmpModuleNetworkParameterEntry
		MAX-ACCESS not-accessible
		STATUS current
		DESCRIPTION
				"Module Network Parameter Entries"
		INDEX { speedAmpIndex }
		::= { speedAmpModuleNetworkParameterTable 1 }

	SpeedAmpModuleNetworkParameterEntry ::=
		SEQUENCE
		{
			speedAmpMSlot INTEGER,
			speedAmpMNetworkAdress IpAddress,
			speedAmpMNetworkMask IpAddress,
			speedAmpMNetworkGateway IpAddress,
			speedAmpMNetworkSnmpTrapSink1 IpAddress,
			speedAmpMNetworkSnmpTrapSink2 IpAddress,
			speedAmpMNetworkSnmpTrapSink3 IpAddress,
			speedAmpMNetworkSnmpTrapSink4 IpAddress,
			speedAmpMNetworkSnmpTrapSink5 IpAddress,
			speedAmpMNetworkSnmpReadCommunity DisplayString,
			speedAmpMNetworkSnmpWriteCommunity DisplayString,
			speedAmpMNetworkSysLocation DisplayString,
			speedAmpMNetworkSnmpAgentStatus INTEGER,
			speedAmpMNetworkHttpServerStatus INTEGER,
			speedAmpMNetworkSysname DisplayString,
			speedAmpNNetworkSyscontact DisplayString,
			speedAmpMNetworkUserTimeout INTEGER,
			speedAmpMNetworkAccess INTEGER
		}

	speedAmpMNetworkAdress OBJECT-TYPE
		SYNTAX IpAddress
		MAX-ACCESS  read-write
		STATUS  current
		DESCRIPTION
			"IP-address of the Ethernet interface"
		DEFVAL { 'c0a80065'H }	-- 192.168.0.101
		::= { speedAmpModuleNetworkParameterEntry 3 }

	speedAmpMNetworkMask OBJECT-TYPE
		SYNTAX IpAddress
		MAX-ACCESS  read-write
		STATUS  current
		DESCRIPTION
			"IP-netmask of the Ethernet interface"
		DEFVAL { 'ffffff00'H }	-- 255.255.255.0
		::= { speedAmpModuleNetworkParameterEntry 4 }

	speedAmpMNetworkGateway OBJECT-TYPE
		SYNTAX IpAddress
		MAX-ACCESS  read-write
		STATUS  current
		DESCRIPTION
			"default gateway of the Ethernet interface"
		DEFVAL { '00000000'H }
		::= { speedAmpModuleNetworkParameterEntry 5 }

	speedAmpMNetworkSnmpTrapSink1 OBJECT-TYPE
		SYNTAX IpAddress
		MAX-ACCESS  read-write
		STATUS  current
		DESCRIPTION
			"Trap destination 1 for SNMP traps. Clear value is 0.0.0.0"
		DEFVAL { '00000000'H }
		::= { speedAmpModuleNetworkParameterEntry 6 }

	speedAmpMNetworkSnmpTrapSink2 OBJECT-TYPE
		SYNTAX IpAddress
		MAX-ACCESS  read-write
		STATUS  current
		DESCRIPTION
			"Trap destination 2 for SNMP traps. Clear value is 0.0.0.0"
		DEFVAL { '00000000'H }
		::= { speedAmpModuleNetworkParameterEntry 7 }

	speedAmpMNetworkSnmpTrapSink3 OBJECT-TYPE
		SYNTAX IpAddress
		MAX-ACCESS  read-write
		STATUS  current
		DESCRIPTION
			"Trap destination 3 for SNMP traps. Clear value is 0.0.0.0"
		DEFVAL { '00000000'H }
		::= { speedAmpModuleNetworkParameterEntry 8 }

	speedAmpMNetworkSnmpTrapSink4 OBJECT-TYPE
		SYNTAX IpAddress
		MAX-ACCESS  read-write
		STATUS  current
		DESCRIPTION
			"Trap destination 4 for SNMP traps. Clear value is 0.0.0.0"
		DEFVAL { '00000000'H }
		::= { speedAmpModuleNetworkParameterEntry 9 }

	speedAmpMNetworkSnmpTrapSink5 OBJECT-TYPE
		SYNTAX IpAddress
		MAX-ACCESS  read-write
		STATUS  current
		DESCRIPTION
			"Trap destination 5 for SNMP traps. Clear value is 0.0.0.0"
		DEFVAL { '00000000'H }
		::= { speedAmpModuleNetworkParameterEntry 10 }

	speedAmpMNetworkSnmpReadCommunity OBJECT-TYPE
		SYNTAX DisplayString (SIZE(0..33))
		MAX-ACCESS  read-write
		STATUS  current
		DESCRIPTION
			"SNMP read community name"
		DEFVAL { "public" }
		::= { speedAmpModuleNetworkParameterEntry 11 }

	speedAmpMNetworkSnmpWriteCommunity OBJECT-TYPE
		SYNTAX DisplayString (SIZE(0..33))
		MAX-ACCESS  read-write
		STATUS  current
		DESCRIPTION
			"SNMP write community name"
		DEFVAL { "private" }
		::= { speedAmpModuleNetworkParameterEntry 12 }

	speedAmpMNetworkSysLocation OBJECT-TYPE
		SYNTAX DisplayString (SIZE(0..33))
		MAX-ACCESS  read-write
		STATUS  current
		DESCRIPTION
			"location of the SPEED-Amplifier System"
		DEFVAL { "serverroom" }
		::= { speedAmpModuleNetworkParameterEntry 13 }

	speedAmpMNetworkSnmpAgentStatus OBJECT-TYPE
		SYNTAX INTEGER
		{
			notAvailable(0),
			down(1),
			up(2),
			notImplemented(254),
			unknown(255)
		}
		MAX-ACCESS read-only
		STATUS current
		DESCRIPTION
			"Module Snmp-Agent operational status"
		::= { speedAmpModuleNetworkParameterEntry 14 }

	speedAmpMNetworkHttpServerStatus OBJECT-TYPE
		SYNTAX INTEGER
		{
			notAvailable(0),
			down(1),
			up(2),
			notImplemented(254),
			unknown(255)
		}
		MAX-ACCESS read-only
		STATUS current
		DESCRIPTION
			"Module Snmp-Agent operational status"
		::= { speedAmpModuleNetworkParameterEntry 15 }

	speedAmpMNetworkSysname OBJECT-TYPE
		SYNTAX DisplayString (SIZE(0..33))
		MAX-ACCESS  read-write
		STATUS  current
		DESCRIPTION
			"location of the SPEED-Amplifier System"
		DEFVAL { "serverroom" }
		::= { speedAmpModuleNetworkParameterEntry 16 }

	speedAmpNNetworkSyscontact OBJECT-TYPE
		SYNTAX DisplayString (SIZE(0..33))
		MAX-ACCESS  read-write
		STATUS  current
		DESCRIPTION
			"location of the SPEED-Amplifier System"
		DEFVAL { "serverroom" }
		::= { speedAmpModuleNetworkParameterEntry 17 }

	speedAmpMNetworkUserTimeout OBJECT-TYPE
		SYNTAX INTEGER (120..3600)
		MAX-ACCESS read-only
		STATUS current
		DESCRIPTION
			"Command line access mode"
		::= { speedAmpModuleNetworkParameterEntry 18 }

	speedAmpMNetworkAccess OBJECT-TYPE
		SYNTAX INTEGER
		{
			notavailable(0),
			off(1),
			telnet(2),
			ssh2(3),
			notImplemented(254),
			unknown(255)
		}
		MAX-ACCESS read-only
		STATUS current
		DESCRIPTION
			"Command line access mode"
		::= { speedAmpModuleNetworkParameterEntry 19 }

-- ****************************
-- SpeedAmpModuleEthPortOverview
	speedAmpModuleEthPortOverviewTable OBJECT-TYPE
		SYNTAX SEQUENCE OF SpeedAmpModuleEthPortOverviewEntry
		MAX-ACCESS not-accessible
		STATUS current
		DESCRIPTION
			"SPEED-AMPLIFIER Module Ethernet port overview table"
		::= { speedAmp 5 }

	speedAmpModuleEthPortOverviewEntry OBJECT-TYPE
		SYNTAX SpeedAmpModuleEthPortOverviewEntry
		MAX-ACCESS not-accessible
		STATUS current
		DESCRIPTION
			"port overview entries"
		INDEX { speedAmpIndex }
		::= { speedAmpModuleEthPortOverviewTable 1 }

	SpeedAmpModuleEthPortOverviewEntry ::=
		SEQUENCE
		{
			speedAmpMEthSlot INTEGER,
			speedAmpMEthPort INTEGER,
			speedAmpMEthPortname DisplayString,
			speedAmpMEthPortAdminState INTEGER,
			speedAmpMEthPortOperState INTEGER,
			speedAmpMEthPortMode INTEGER,
			speedAmpMEthSFPState INTEGER,
			speedAmpMEthPortRxPackets INTEGER,
			speedAmpMEthPortTxPackets INTEGER,
			speedAmpMEthErrors INTEGER
		}

	speedAmpMEthSlot OBJECT-TYPE
		SYNTAX INTEGER (1..17)
		MAX-ACCESS read-only
		STATUS current
		DESCRIPTION
			"number of Module Eth port"
		::= { speedAmpModuleEthPortOverviewEntry 2 }

	speedAmpMEthPort OBJECT-TYPE
		SYNTAX INTEGER (0..5)
		MAX-ACCESS read-only
		STATUS current
		DESCRIPTION
			"number of Module Eth port"
		::= { speedAmpModuleEthPortOverviewEntry 3 }

	speedAmpMEthPortname OBJECT-TYPE
		SYNTAX DisplayString (SIZE (0..32))
		MAX-ACCESS read-only
		STATUS current
		DESCRIPTION
			"Port description or port name."
		::= { speedAmpModuleEthPortOverviewEntry 4 }

	speedAmpMEthPortAdminState OBJECT-TYPE
		SYNTAX INTEGER
		{
			notAvailable(0),
			adminDown(1),
			adminUp(2),
			unknown(255)
		}
		MAX-ACCESS read-only
		STATUS current
		DESCRIPTION
			"administrativ port status"
		::= { speedAmpModuleEthPortOverviewEntry 5 }

	speedAmpMEthPortOperState OBJECT-TYPE
		SYNTAX INTEGER
		{
			notAvailable(0),
			down(1),
			up(2),
			unknown(255)
		}
		MAX-ACCESS read-only
		STATUS current
		DESCRIPTION
			"Module Eth Port operational status"
		::= { speedAmpModuleEthPortOverviewEntry 6 }

	speedAmpMEthPortMode OBJECT-TYPE
		SYNTAX INTEGER
		{
			notAvailable(0),
			autoneg(1),
			10HDX(2),
			10FDX(3),
			100HDX(4),
			100FDX(5),
			hdlc(6),
			rmii(7),
			unknown(255)
		}
		MAX-ACCESS read-only
		STATUS current
		DESCRIPTION
			"Module Eth Port Configuration Mode."
		::= { speedAmpModuleEthPortOverviewEntry 7 }

	speedAmpMEthSFPState OBJECT-TYPE
		SYNTAX INTEGER
		{
			notAvailable(0),
			sfpOperDown(1),
			sfpOperUp(2),
			sfpTxFault(3),
			sfpInstalled(4),
			sfpRemoved(5),
			sfpNotPossible(6),
			unknown(255)
		}
		MAX-ACCESS read-only
		STATUS current
		DESCRIPTION
			"SFP installed / alarm status"
		::= { speedAmpModuleEthPortOverviewEntry 8 }

	speedAmpMEthPortRxPackets OBJECT-TYPE
		SYNTAX INTEGER
		MAX-ACCESS read-only
		STATUS current
		DESCRIPTION
			"Module Eth Port received Packets"
		::= { speedAmpModuleEthPortOverviewEntry 9 }

	speedAmpMEthPortTxPackets OBJECT-TYPE
		SYNTAX INTEGER
		MAX-ACCESS read-only
		STATUS current
		DESCRIPTION
			"Module Eth Port transmitted Packets"
		::= { speedAmpModuleEthPortOverviewEntry 10 }

	speedAmpMEthErrors OBJECT-TYPE
		SYNTAX INTEGER
		MAX-ACCESS read-only
		STATUS current
		DESCRIPTION
			"Module Eth Port received Errors"
		::= { speedAmpModuleEthPortOverviewEntry 11 }


--********************************************
-- SpeedAmpModulePortConfig

	speedAmpMEthPortConfigTable OBJECT-TYPE
		SYNTAX SEQUENCE OF SpeedAmpMEthPortConfigEntry
		MAX-ACCESS not-accessible
		STATUS current
		DESCRIPTION
				"SPEED-Amplifier Module Ethernet port config table"
		::= { speedAmp 6 }

	speedAmpMEthPortConfigEntry OBJECT-TYPE
		SYNTAX SpeedAmpMEthPortConfigEntry
		MAX-ACCESS not-accessible
		STATUS current
		DESCRIPTION
				"port config Entries"
		INDEX { speedAmpIndex }
		::= { speedAmpMEthPortConfigTable 1 }

	SpeedAmpMEthPortConfigEntry ::=
		SEQUENCE
		{
			speedAmpMEthSlot		INTEGER,
			speedAmpMEthPort 		INTEGER,
			speedAmpMEthPCfgAdminConfig 	INTEGER,
			speedAmpMEthPCfgDescription 	DisplayString,
			speedAmpMEthPCfgMode 		INTEGER,
			speedAmpMEthPCfgAlarmReporting	INTEGER,
			speedAmpMEthPCfgAlarmSchedule	INTEGER
		}

	speedAmpMEthPCfgAdminConfig OBJECT-TYPE
		SYNTAX INTEGER
		{
			notAvailable(0),
			adminDown(1),
			adminUp(2),
			unknown(255)
		}
		MAX-ACCESS read-write
		STATUS current
		DESCRIPTION
			"Module Ethernet port administrative configuration. Only ports 1..4 are configurable."
		::= { speedAmpMEthPortConfigEntry 4 }

	speedAmpMEthPCfgDescription OBJECT-TYPE
		SYNTAX DisplayString (SIZE (0..32))
		MAX-ACCESS read-write
		STATUS current
		DESCRIPTION
			"Module Ethernet port description. Only ports 1..3 are configurable."
		::= { speedAmpMEthPortConfigEntry 5 }

	speedAmpMEthPCfgMode OBJECT-TYPE
		SYNTAX INTEGER
		{
			notAvailable(0),
			autoneg(1),
			fix10HDX(2),
			fix10FDX(3),
			fix100HDX(4),
			fix100FDX(5),
			fixhdlc(6),
			fixrmii(7),
			unknown(255)
		}
		MAX-ACCESS read-write
		STATUS current
		DESCRIPTION
			"Module Ethernet Port Configuration. Only ports 1 and 2 are configurable."
		::= { speedAmpMEthPortConfigEntry 6 }

	speedAmpMEthPCfgAlarmReporting OBJECT-TYPE
		SYNTAX INTEGER
		{
			notAvailable(0),
			AlarmReportingEnabled(1),
			AlarmReportingDisabledbySchedule(2),
			AlarmReportingDisabledPermanent(3),
			unknown(255)
		}
		MAX-ACCESS read-write
		STATUS current
		DESCRIPTION
			"Ethernet port alarm deactivation. Only applicable for user SFP!"
		::= { speedAmpMEthPortConfigEntry 7 }

	speedAmpMEthPCfgAlarmSchedule OBJECT-TYPE
		SYNTAX INTEGER (0..1200)
		MAX-ACCESS read-write
		STATUS current
		DESCRIPTION
			"Ethernet port alarm deactivation schedule. Value in hours. After this time has elapsed, the alarms are active again. Only applicable for user SFP!"
		::= { speedAmpMEthPortConfigEntry 8 }

--***************************************
-- SpeedAmpModuleGeneralSFPInfos

	speedAmpModuleGeneralSFPInfosTable OBJECT-TYPE
		SYNTAX SEQUENCE OF SpeedAmpModuleGeneralSFPInfosEntry
		MAX-ACCESS not-accessible
		STATUS current
		DESCRIPTION
				"SPEED-AMPLIFIER SFP general information table"
		::= { speedAmp 7 }

	speedAmpModuleGeneralSFPInfosEntry OBJECT-TYPE
		SYNTAX SpeedAmpModuleGeneralSFPInfosEntry
		MAX-ACCESS not-accessible
		STATUS current
		DESCRIPTION
				"Module SFP general information Entries"
		INDEX { speedAmpIndex }
		::= { speedAmpModuleGeneralSFPInfosTable 1 }

	SpeedAmpModuleGeneralSFPInfosEntry ::=
		SEQUENCE
		{
			speedAmpMSFPSlot		INTEGER,
			speedAmpMSFPPort		INTEGER,
			speedAmpSFPVendorName		DisplayString,
			speedAmpSFPPartNumber		DisplayString,
			speedAmpSFPSerialNumber		DisplayString,
			speedAmpSFPWavelength		INTEGER,
			speedAmpSFPDMIMode		INTEGER,
			speedAmpSFPPortType		INTEGER
		}

	speedAmpMSFPSlot OBJECT-TYPE
		SYNTAX INTEGER
		MAX-ACCESS read-only
		STATUS current
		DESCRIPTION
				"SFP slot"
		::= { speedAmpModuleGeneralSFPInfosEntry 2 }

	speedAmpMSFPPort OBJECT-TYPE
		SYNTAX INTEGER
		MAX-ACCESS read-only
		STATUS current
		DESCRIPTION
				"SFP port"
		::= { speedAmpModuleGeneralSFPInfosEntry 3 }

	speedAmpSFPVendorName OBJECT-TYPE
		SYNTAX DisplayString (SIZE (0..17))
		MAX-ACCESS  read-only
		STATUS  current
		DESCRIPTION
				"SFP vendor name"
		::= { speedAmpModuleGeneralSFPInfosEntry 4 }

	speedAmpSFPPartNumber OBJECT-TYPE
		SYNTAX DisplayString (SIZE (0..17))
		MAX-ACCESS  read-only
		STATUS  current
		DESCRIPTION
				"SFP part number"
		::= { speedAmpModuleGeneralSFPInfosEntry 5 }

	speedAmpSFPSerialNumber OBJECT-TYPE
		SYNTAX DisplayString (SIZE (0..17))
		MAX-ACCESS  read-only
		STATUS  current
		DESCRIPTION
				"SFP serial number"
		::= { speedAmpModuleGeneralSFPInfosEntry 6 }

	speedAmpSFPWavelength OBJECT-TYPE
		SYNTAX INTEGER
		MAX-ACCESS  read-only
		STATUS  current
		DESCRIPTION
				"SFP wavelength in units of 100*(value of 1nm)"
		::= { speedAmpModuleGeneralSFPInfosEntry 7 }

	speedAmpSFPDMIMode OBJECT-TYPE
		SYNTAX INTEGER
		{
			notAvailable(0),
			sff8472V93(1),
			sff8472V95(2),
			sff8472V102(3),
			sffVother(4),
			notImplemented(254),
			unknown(255)
		}
		MAX-ACCESS  read-only
		STATUS  current
		DESCRIPTION
				"SFP DMI Type "
		::= { speedAmpModuleGeneralSFPInfosEntry 8 }

	speedAmpSFPPortType OBJECT-TYPE
		SYNTAX INTEGER
		{
			notAvailable(0),
			osc(1),
			user(2),
			unknown(255)
		}
		MAX-ACCESS  read-only
		STATUS  current
		DESCRIPTION
				"SFP Port Type "
		::= { speedAmpModuleGeneralSFPInfosEntry 9 }

-- ****************************************
-- SpeedAmpModuleSFPMessurement

	speedAmpModuleSFPMessurementTable OBJECT-TYPE
		SYNTAX SEQUENCE OF SpeedAmpModuleSFPMessurementEntry
		MAX-ACCESS not-accessible
		STATUS current
		DESCRIPTION
				"SPEED-AMPLIFIER SFP messurement table"
		::= { speedAmp 8 }

	speedAmpModuleSFPMessurementEntry OBJECT-TYPE
		SYNTAX SpeedAmpModuleSFPMessurementEntry
		MAX-ACCESS not-accessible
		STATUS current
		DESCRIPTION
				"SFP messurement Entries"
		INDEX { speedAmpIndex }
		::= { speedAmpModuleSFPMessurementTable 1 }

	SpeedAmpModuleSFPMessurementEntry ::=
		SEQUENCE
		{
			speedAmpMSFPSlot	INTEGER,
			speedAmpMSFPPort	INTEGER,
			speedAmpMSFPRXPower	INTEGER,
			speedAmpMSFPTXPower	INTEGER,
			speedAmpMSFPTXBias	INTEGER,
			speedAmpMSFPTemp	INTEGER,
			speedAmpMSFPPortType	INTEGER
		}

	speedAmpMSFPRXPower OBJECT-TYPE
		SYNTAX INTEGER
		MAX-ACCESS  read-only
		STATUS  current
		DESCRIPTION
				"SFP optical receive power in units of 10*(value of 1dbm)"
		::= { speedAmpModuleSFPMessurementEntry 4 }

	speedAmpMSFPTXPower OBJECT-TYPE
		SYNTAX INTEGER
		MAX-ACCESS  read-only
		STATUS  current
		DESCRIPTION
				"SFP optical transmit power in units of 10*(value of 1dbm)"
		::= { speedAmpModuleSFPMessurementEntry 5 }

	speedAmpMSFPTXBias OBJECT-TYPE
		SYNTAX INTEGER
		MAX-ACCESS  read-only
		STATUS  current
		DESCRIPTION
				"SFP TX Bias in units of  1mA "
		::= { speedAmpModuleSFPMessurementEntry 6 }

	speedAmpMSFPTemp OBJECT-TYPE
		SYNTAX INTEGER
		MAX-ACCESS  read-only
		STATUS  current
		DESCRIPTION
				"SFP temperature in units of 1degree Centigrade"
		::= { speedAmpModuleSFPMessurementEntry 7 }

	speedAmpMSFPPortType OBJECT-TYPE
		SYNTAX INTEGER
		{
			notAvailable(0),
			osc(1),
			user(2),
			unknown(255)
		}
		MAX-ACCESS  read-only
		STATUS  current
		DESCRIPTION
				"SFP Port Type "
		::= { speedAmpModuleSFPMessurementEntry 8 }

--***************************************
-- SpeedAmpDeviceGeneralInfos

	speedAmpDevGeneralInfosTable OBJECT-TYPE
		SYNTAX SEQUENCE OF SpeedAmpDevGeneralInfosEntry
		MAX-ACCESS not-accessible
		STATUS current
		DESCRIPTION
				"SPEED-AMPLIFIER Amplifier device general information table"
		::= { speedAmp 9 }

	speedAmpDevGeneralInfosEntry OBJECT-TYPE
		SYNTAX SpeedAmpDevGeneralInfosEntry
		MAX-ACCESS not-accessible
		STATUS current
		DESCRIPTION
				"Amplifier device general information Entries"
		INDEX { speedAmpIndex }
		::= { speedAmpDevGeneralInfosTable 1 }

	SpeedAmpDevGeneralInfosEntry ::=
		SEQUENCE
		{
			speedAmpMSlot			 INTEGER,
			speedAmpDevSerialNumber		 DisplayString,
			speedAmpDevConfiguration	 INTEGER,
			speedAmpDevModuletype		 INTEGER,
			speedAmpDevVersion		 DisplayString,
			speedAmpDevVendor		 INTEGER,
			speedAmpDevLinePortDescription	 DisplayString,
			speedAmpDevClientPortDescription DisplayString
		}

	speedAmpDevSerialNumber OBJECT-TYPE
		SYNTAX DisplayString (SIZE (0..17))
		MAX-ACCESS  read-only
		STATUS  current
		DESCRIPTION
				"Amplifier Device Serial Number"
		::= { speedAmpDevGeneralInfosEntry 3 }

	speedAmpDevConfiguration OBJECT-TYPE
		SYNTAX INTEGER
		{
			notAvailable(0),
			confConstantPower(3),
			confConstantGain(4),
			confOFF(5),
			confOther(6),
			unknown(255)
		}
		MAX-ACCESS  read-only
		STATUS  current
		DESCRIPTION
				"Amplifier Device Configuration"
		::= { speedAmpDevGeneralInfosEntry 4 }

	speedAmpDevModuletype OBJECT-TYPE
		SYNTAX INTEGER
		{
			notAvailable (0),
			other(1),
			preamp14(2),
			preamp17(3),
			booster17(4),
			booster23(5),
			inline17(6),
			inline23(7),
			Unknown (255)
		}
		MAX-ACCESS  read-only
		STATUS  current
		DESCRIPTION
				"Amplifier Device Type"
		::= { speedAmpDevGeneralInfosEntry 5 }

	speedAmpDevVersion OBJECT-TYPE
		SYNTAX DisplayString (SIZE (0..17))
		MAX-ACCESS  read-only
		STATUS  current
		DESCRIPTION
				"Amplifier Device Version Code "
		::= { speedAmpDevGeneralInfosEntry 6 }

	speedAmpDevVendor OBJECT-TYPE
		SYNTAX INTEGER
		MAX-ACCESS  read-only
		STATUS  current
		DESCRIPTION
				"Amplifier Device Vendor Code"
		::= { speedAmpDevGeneralInfosEntry 7 }

	speedAmpDevLinePortDescription OBJECT-TYPE
		SYNTAX DisplayString (SIZE (0..32))
		MAX-ACCESS  read-only
		STATUS  current
		DESCRIPTION
				"Amplifier Optical Line Port Description String "
		::= { speedAmpDevGeneralInfosEntry 8 }

	speedAmpDevClientPortDescription OBJECT-TYPE
		SYNTAX DisplayString (SIZE (0..32))
		MAX-ACCESS  read-only
		STATUS  current
		DESCRIPTION
				"Amplifier Optical Client Port Description String "
		::= { speedAmpDevGeneralInfosEntry 9 }

--***************************************
-- SpeedAmpDeviceOverview

	speedAmpDevOverviewTable OBJECT-TYPE
		SYNTAX SEQUENCE OF SpeedAmpDevOverviewEntry
		MAX-ACCESS not-accessible
		STATUS current
		DESCRIPTION
				"SPEED-AMPLIFIER Amplifier device Overview table"
		::= { speedAmp 10 }

	speedAmpDevOverviewEntry OBJECT-TYPE
		SYNTAX SpeedAmpDevOverviewEntry
		MAX-ACCESS not-accessible
		STATUS current
		DESCRIPTION
				"Amplifier device Overview Entries"
		INDEX { speedAmpIndex }
		::= { speedAmpDevOverviewTable 1 }

	SpeedAmpDevOverviewEntry ::=
		SEQUENCE
		{
			speedAmpMSlot			INTEGER,
			speedAmpDevGain			INTEGER,
			speedAmpDevPumpCurrent		INTEGER,
			speedAmpDevPumpPower		INTEGER,
			speedAmpDevMode			INTEGER,
			speedAmpDevModeShutdown		INTEGER,
			speedAmpDevLosInputThreshold	INTEGER,
			speedAmpDevHighOutputThreshold	INTEGER,
			speedAmpDevAlarm		INTEGER,
			speedAmpDevCaseTemperature	INTEGER,
			speedAmpDevClientInputPower	INTEGER,
			speedAmpDevLineOutputPower	INTEGER
		}

	speedAmpDevGain OBJECT-TYPE
		SYNTAX INTEGER
		MAX-ACCESS  read-only
		STATUS  current
		DESCRIPTION
				"Amplifier optical Gain in units of 100*(value of 1db)"
		::= { speedAmpDevOverviewEntry 3 }

	speedAmpDevPumpCurrent OBJECT-TYPE
		SYNTAX INTEGER
		MAX-ACCESS  read-only
		STATUS  current
		DESCRIPTION
				"Amplifier Pump Current in units of 10*(value of 1mA)"
		::= { speedAmpDevOverviewEntry 4 }

	speedAmpDevPumpPower OBJECT-TYPE
		SYNTAX INTEGER
		MAX-ACCESS  read-only
		STATUS  current
		DESCRIPTION
				"Amplifier Pump Power in units of 10*(value of 1mW)"
		::= { speedAmpDevOverviewEntry 5 }

	speedAmpDevMode OBJECT-TYPE
		SYNTAX INTEGER
		{
			notAvailable(0),
			confConstantPower(3),
			confConstantGain(4),
			confOFF(5),
			confOther(6),
			unknown(255)
		}
		MAX-ACCESS  read-only
		STATUS  current
		DESCRIPTION
				"Amplifier Working Mode"
		::= { speedAmpDevOverviewEntry 6 }

	speedAmpDevModeShutdown OBJECT-TYPE
		SYNTAX	INTEGER
		{
			notAvailable (0),
			cfgAutoLaserShutdownOff (1),
			cfgAutoLaserShutdownOn (2),
			unknown (255)
		}
		ACCESS	read-only
		STATUS  current
		DESCRIPTION
				"Amplifier Shutdown Mode"
		::= { speedAmpDevOverviewEntry 7 }

	speedAmpDevLosInputThreshold OBJECT-TYPE
		SYNTAX INTEGER
		MAX-ACCESS  read-only
		STATUS  current
		DESCRIPTION
				"Amplifier Loss of Input Power Threshold in units of 100*(value of 1dbm). Range: -45.00 to 0.00 dBm"
		::= { speedAmpDevOverviewEntry 8 }

	speedAmpDevHighOutputThreshold OBJECT-TYPE
		SYNTAX INTEGER
		MAX-ACCESS  read-only
		STATUS  current
		DESCRIPTION
				"Amplifier Output High Power Threshold in units of 100*(value of 1dbm)"
		::= { speedAmpDevOverviewEntry 9 }

	speedAmpDevAlarm OBJECT-TYPE
		SYNTAX INTEGER
		{
			noAlarm (0),
			unknown (254)
		}
		MAX-ACCESS  read-only
		STATUS  current
		DESCRIPTION
				"Amplifier Alarm Status - Error code from amp module"
		::= { speedAmpDevOverviewEntry 10 }

	speedAmpDevCaseTemperature OBJECT-TYPE
		SYNTAX INTEGER
		MAX-ACCESS  read-only
		STATUS  current
		DESCRIPTION
				"Amplifier module case temperature (value of 1degree Centigrade)"
		::= { speedAmpDevOverviewEntry 11 }

	speedAmpDevClientInputPower OBJECT-TYPE
		SYNTAX INTEGER
		MAX-ACCESS  read-only
		STATUS  current
		DESCRIPTION
				"Amplifier optical client Input Power in units of 100*(value of 1dbm)"
		::= { speedAmpDevOverviewEntry 12 }

	speedAmpDevLineOutputPower OBJECT-TYPE
		SYNTAX INTEGER
		MAX-ACCESS  read-only
		STATUS  current
		DESCRIPTION
				"Amplifier optical line Output Power in units of 100*(value of 1dbm)"
		::= { speedAmpDevOverviewEntry 13 }

-- *********************************
-- SpeedAmpDeviceConfig

	speedAmpDevConfigTable OBJECT-TYPE
		SYNTAX SEQUENCE OF SpeedAmpDevConfigEntry
		MAX-ACCESS not-accessible
		STATUS current
		DESCRIPTION
			"SPEED-AMPLIFIER Dev Config Table"
		::= { speedAmp 11 }

	speedAmpDevConfigEntry OBJECT-TYPE
		SYNTAX SpeedAmpDevConfigEntry
		MAX-ACCESS not-accessible
		STATUS current
		DESCRIPTION
			"Device Configuration Entries"
		INDEX { speedAmpIndex }
		::= { speedAmpDevConfigTable 1 }

	SpeedAmpDevConfigEntry ::=
		SEQUENCE
		{
			speedAmpMSlot				INTEGER,
			speedAmpDevCfgGainValue			INTEGER,
			speedAmpDevCfgPoutValue			INTEGER,
			speedAmpDevCfgPumpCurrentValue		INTEGER,
			speedAmpDevCfgModeValue			INTEGER,
			speedAmpDevCfgShutdownModeValue		INTEGER,
			speedAmpDevCfgLosInputThresholdValue	INTEGER,
			speedAmpDevCfgLinePortDescription	DisplayString,
			speedAmpDevCfgClientPortDescription	DisplayString,
			speedAmpDevCfgAlarmReporting		INTEGER,
			speedAmpDevCfgAlarmSchedule		INTEGER
		}

	speedAmpDevCfgGainValue OBJECT-TYPE
		SYNTAX	INTEGER
		MAX-ACCESS	read-write
		STATUS	current
		DESCRIPTION
			"Amplifier optical Gain Value in units of 100*(value of 1db)"
		::= { speedAmpDevConfigEntry 3}

	speedAmpDevCfgPoutValue OBJECT-TYPE
		SYNTAX	INTEGER
		MAX-ACCESS	read-write
		STATUS	current
		DESCRIPTION
			"Amplifier Optical Output Power in units of 100*(value of 1dbm)"
		::= { speedAmpDevConfigEntry 4}

	speedAmpDevCfgPumpCurrentValue OBJECT-TYPE
		SYNTAX	INTEGER
		{
			notAvailable(0),
			notImplemented(254),
			unknown(255)
		}
		MAX-ACCESS	read-only
		STATUS	current
		DESCRIPTION
			"Amplifier Pump Current in units of 10*(value of 1mA)"
		::= { speedAmpDevConfigEntry 5}

	speedAmpDevCfgModeValue OBJECT-TYPE
		SYNTAX INTEGER
		{
			notAvailable(0),
			confConstantPower(3),
			confConstantGain(4),
			confOFF(5),
			confOther(6),
			unknown(255)
		}
		MAX-ACCESS	read-write
		STATUS	current
		DESCRIPTION
			"Amplifier Working Mode"
		::= { speedAmpDevConfigEntry 6}

	speedAmpDevCfgShutdownModeValue OBJECT-TYPE
		SYNTAX	INTEGER
		{
			notAvailable (0),
			cfgAutoLaserShutdownOff (1),
			cfgAutoLaserShutdownOn (2),
			unknown (255)
		}
		MAX-ACCESS	read-write
		STATUS	current
		DESCRIPTION
			"Amplifier Shutdown Working Mode"
		::= { speedAmpDevConfigEntry 7}

	speedAmpDevCfgLosInputThresholdValue OBJECT-TYPE
		SYNTAX	INTEGER
		MAX-ACCESS	read-write
		STATUS	current
		DESCRIPTION
			"Amplifier optical Input Value LOS Threshold in units of 100*(value of 1dbm)"
		::= { speedAmpDevConfigEntry 8}

	speedAmpDevCfgLinePortDescription OBJECT-TYPE
		SYNTAX DisplayString (SIZE (0..32))
		MAX-ACCESS  read-write
		STATUS  current
		DESCRIPTION
				"Amplifier Optical Line Port Description String "
		::= { speedAmpDevConfigEntry 9}

	speedAmpDevCfgClientPortDescription OBJECT-TYPE
		SYNTAX DisplayString (SIZE (0..32))
		MAX-ACCESS  read-write
		STATUS  current
		DESCRIPTION
				"Amplifier Optical Client Port Description String "
		::= { speedAmpDevConfigEntry 10}

	speedAmpDevCfgAlarmReporting OBJECT-TYPE
		SYNTAX INTEGER
		{
			notAvailable(0),
			AlarmReportingEnabled(1),
			AlarmReportingDisabledbySchedule(2),
			AlarmReportingDisabledPermanent(3),
			unknown(255)
		}
		MAX-ACCESS read-write
		STATUS current
		DESCRIPTION
			"Amp module alarm deactivation"
		::= { speedAmpDevConfigEntry 11 }

	speedAmpDevCfgAlarmSchedule OBJECT-TYPE
		SYNTAX INTEGER (0..1200)
		MAX-ACCESS read-write
		STATUS current
		DESCRIPTION
			"Amp module alarm deactivation schedule. Value in hours. After this time has elapsed, the alarms are active again."
		::= { speedAmpDevConfigEntry 12 }


--***************************************
-- SpeedAmpDeviceAlarmTable

	speedAmpDevAlarmTable OBJECT-TYPE
		SYNTAX SEQUENCE OF SpeedAmpDevAlarmEntry
		MAX-ACCESS not-accessible
		STATUS current
		DESCRIPTION
				"SPEED-AMPLIFIER Amplifier device Alarm table"
		::= { speedAmp 12 }

	speedAmpDevAlarmEntry OBJECT-TYPE
		SYNTAX SpeedAmpDevAlarmEntry
		MAX-ACCESS not-accessible
		STATUS current
		DESCRIPTION
				"Amplifier device Alarm Entries"
		INDEX { speedAmpIndex }
		::= { speedAmpDevAlarmTable 1 }

	SpeedAmpDevAlarmEntry ::=
		SEQUENCE
		{
			speedAmpMSlot				INTEGER,
			speedAmpDevAlarmOpticalInput		INTEGER,
			speedAmpDevAlarmOpticalOutput		INTEGER,
			speedAmpDevAlarmModuleTemperature	INTEGER,
			speedAmpDevAlarmPumpTemperature		INTEGER,
			speedAmpDevAlarmPumpDriveCurrent	INTEGER,
			speedAmpDevAlarmSupplyVoltage		INTEGER,
			speedAmpDevAlarmAutoshutdown		INTEGER,
			speedAmpDevAlarmSecurityMonitor		INTEGER
		}

	speedAmpDevAlarmOpticalInput OBJECT-TYPE
		SYNTAX INTEGER
		{
			notAvailiable (0),
			noAlarm(1),
			activeAlarm(2),
			unknown (255)
		}
		MAX-ACCESS  read-only
		STATUS  current
		DESCRIPTION
				"Amplifier optical Input Value is under specified Threshold Value"
		::= { speedAmpDevAlarmEntry 3 }

	speedAmpDevAlarmOpticalOutput OBJECT-TYPE
		SYNTAX INTEGER
		{
			notAvailiable (0),
			noAlarm(1),
			activeAlarm(2),
			unknown (255)
		}
		MAX-ACCESS  read-only
		STATUS  current
		DESCRIPTION
				"Amplifier optical Input Value is over specified Threshold Value"
		::= { speedAmpDevAlarmEntry 4 }

	speedAmpDevAlarmModuleTemperature OBJECT-TYPE
		SYNTAX INTEGER
		{
			notAvailiable (0),
			noAlarm(1),
			activeAlarm(2),
			unknown (255)
		}
		MAX-ACCESS  read-only
		STATUS  current
		DESCRIPTION
				"Amplifier Temperature Value is over specified Threshold Value"
		::= { speedAmpDevAlarmEntry 5 }

	speedAmpDevAlarmPumpTemperature OBJECT-TYPE
		SYNTAX INTEGER
		{
			notAvailiable (0),
			noAlarm(1),
			activeAlarm(2),
			unknown (255)
		}
		MAX-ACCESS  read-only
		STATUS  current
		DESCRIPTION
				"Amplifier Pump Temperature is out of specified Range"
		::= { speedAmpDevAlarmEntry 6 }

	speedAmpDevAlarmPumpDriveCurrent OBJECT-TYPE
		SYNTAX INTEGER
		{
			notAvailiable (0),
			noAlarm(1),
			activeAlarm(2),
			unknown (255)
		}
		MAX-ACCESS  read-only
		STATUS  current
		DESCRIPTION
				"Amplifier Pump Drive Current is out of specified Range"
		::= { speedAmpDevAlarmEntry 7 }

	speedAmpDevAlarmSupplyVoltage OBJECT-TYPE
		SYNTAX INTEGER
		{
			notAvailiable (0),
			noAlarm(1),
			activeAlarm(2),
			unknown (255)
		}
		MAX-ACCESS  read-only
		STATUS  current
		DESCRIPTION
				"Amplifier Supply voltage is out of specified Range"
		::= { speedAmpDevAlarmEntry 8 }

	speedAmpDevAlarmAutoshutdown OBJECT-TYPE
		SYNTAX INTEGER
		{
			notAvailiable (0),
			noAlarm(1),
			activeAlarm(2),
			unknown (255)
		}
		MAX-ACCESS  read-only
		STATUS  current
		DESCRIPTION
				"Amplifier Device Autoshutdown activated"
		::= { speedAmpDevAlarmEntry 9 }

	speedAmpDevAlarmSecurityMonitor OBJECT-TYPE
		SYNTAX INTEGER
		{
			notAvailiable(0),
			secmonready(1),
			secmonhalted(2),
			secmonfailure(3),
			unknown(255)
		}
		MAX-ACCESS  read-only
		STATUS  current
		DESCRIPTION
				"Status of SecurityMonitor"
		::= { speedAmpDevAlarmEntry 10 }


--***************************************
-- SpeedAmpModuleSFPAlarmTable

	speedAmpModuleSFPAlarmTable OBJECT-TYPE
		SYNTAX SEQUENCE OF SpeedAmpModuleSFPAlarmEntry
		MAX-ACCESS not-accessible
		STATUS current
		DESCRIPTION
				"SPEED-AMPLIFIER Module SFP Alarm table"
		::= { speedAmp 13 }

	speedAmpModuleSFPAlarmEntry OBJECT-TYPE
		SYNTAX SpeedAmpModuleSFPAlarmEntry
		MAX-ACCESS not-accessible
		STATUS current
		DESCRIPTION
				"Module SFP Alarm Entries"
		INDEX { speedAmpIndex }
		::= { speedAmpModuleSFPAlarmTable 1 }

	SpeedAmpModuleSFPAlarmEntry ::=
		SEQUENCE
		{
			speedAmpMSFPSlot			INTEGER,
			speedAmpMSFPPort			INTEGER,
			speedAmpMSFPRxPowerAlarm		INTEGER,
			speedAmpMSFPTxPowerAlarm		INTEGER,
			speedAmpMSFPTxBiasAlarm			INTEGER,
			speedAmpMSFPTemperatureAlarm		INTEGER,
			speedAmpMSFPDWDMAlarm			INTEGER
		}

	speedAmpMSFPRxPowerAlarm OBJECT-TYPE
		SYNTAX INTEGER
		{
			notAvailiable(0),
			noAlarm(1),
			rxLowAlarm(2),
			rxHighAlarm(3),
			unknown(255)
		}
		MAX-ACCESS  read-only
		STATUS  current
		DESCRIPTION
				"Module SFP optical Rx Power is out of specified Range"
		::= { speedAmpModuleSFPAlarmEntry 4 }

	speedAmpMSFPTxPowerAlarm OBJECT-TYPE
		SYNTAX INTEGER
		{
			notAvailiable(0),
			noAlarm(1),
			activeAlarm(2),
			unknown(255)
		}
		MAX-ACCESS  read-only
		STATUS  current
		DESCRIPTION
				"Module SFP optical Tx Power is out of specified Range"
		::= { speedAmpModuleSFPAlarmEntry 5 }

	speedAmpMSFPTxBiasAlarm OBJECT-TYPE
		SYNTAX INTEGER
		{
			notAvailiable(0),
			noAlarm(1),
			activeAlarm(2),
			unknown(255)
		}
		MAX-ACCESS  read-only
		STATUS  current
		DESCRIPTION
				"Module SFP Bias Current is out of specified Range"
		::= { speedAmpModuleSFPAlarmEntry 6 }

	speedAmpMSFPTemperatureAlarm OBJECT-TYPE
		SYNTAX INTEGER
		{
			notAvailiable(0),
			noAlarm(1),
			highWarning(2),
			highAlarm(3),
			unknown(255)
		}
		MAX-ACCESS  read-only
		STATUS  current
		DESCRIPTION
				"Module SFP Temperature is out of specified Range"
		::= { speedAmpModuleSFPAlarmEntry 7 }

	speedAmpMSFPDWDMAlarm OBJECT-TYPE
		SYNTAX INTEGER
		{
			notAvailiable(0),
			noAlarm(1),
			activeAlarm(2),
			unknown(255)
		}
		MAX-ACCESS  read-only
		STATUS  current
		DESCRIPTION
				"DWDM SFP - DWDM Alarm"
		::= { speedAmpModuleSFPAlarmEntry 8 }


END
