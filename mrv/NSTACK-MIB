--  =======================================================================
--  File        : nbstack.mib
--  Description : Private MIB for NBase Stackable Device
--  By          : Vaisman Yakov
--  Version     : $Revision:   10.6
--  Date        : $Date:   March 27, 2007
--  =======================================================================
--
--
-- Copyright (c) 1998 NBase Switch Communications.  All Rights Reserved.
--
-- Reproduction of this document is authorized on condition that this
-- copyright notice is included.  This NBase SNMP MIB Specification
-- embodies NBase's proprietary intellectual property.  NBase
-- retains all title and ownership in the specification, including any
-- revisions.
--
-- It is NBase's intent to encourage the widespread use of this
-- specification in connection with the management of NBase's
-- p223roducts. NBase grants vendor, end-users, and other interested
-- parties a non-exclusive license to use this specification in
-- connection with the management of NBase's products.
--
-- This specification is supplied "AS IS," and NBase makes no
-- warranty, either express or implied, as to the use, operation,
-- condition, or performance of the specification.
--
-- NBase retains the right to change this MIB without notification.
--
NSTACK-MIB DEFINITIONS ::= BEGIN

	 IMPORTS
		enterprises,
                IpAddress,TimeTicks           FROM RFC1155-SMI

		OBJECT-TYPE                   FROM RFC-1212
		DisplayString		      FROM RFC1213-MIB;

		PortsBitmap ::= OCTET STRING
	--          		 Set of ports. Each octet
	--                 within the value of this object specifies a set of
	--                 eight ports, with the first octet specifying ports
	--                 1 through 8, the second octet specifying ports 9
	--                 through 16, etc.  Within each octet, the least
	--                 significant bit represents the lowest numbered
	--                 port, and the most significant bit represents the
	--                 highest numbered port.  Thus, each port of the
	--                 switch is represented by a single bit within the
	--                 value of this object.  If that bit has a value of
	--                 <1> then that port is included in the set of
	--                 ports; the port is not included if its bit has a
	--                 value of <0>.  (Note that the setting of the bit
	--                 corresponding to the port from which a frame is
	--                 received is irrelevant.)  The default value of
	--                 this object is a string of ones of appropriate
	--                 length."

-- ************************************************************
-- NBase Object Identifier Definition
-- ************************************************************

nbase              OBJECT IDENTIFIER ::= { enterprises 629 }
nbSwitchG1         OBJECT IDENTIFIER ::= { nbase 1 }
nbSwitchG1Il       OBJECT IDENTIFIER ::= { nbSwitchG1 50}
nbsStackInfo       OBJECT IDENTIFIER ::= { nbSwitchG1Il 4}

-- ************************************************************

-- ************************************************************
-- Objects in the Stack Information Group
-- *************************************************************

	 nbsStackSlotCapacity  OBJECT-TYPE
	 SYNTAX    INTEGER
         ACCESS    read-only
         STATUS    mandatory
         DESCRIPTION
                 "Max quantity of Slots possible in the Stack."
		 ::= { nbsStackInfo 1 }

	 nbsStackSlotsTableSize    OBJECT-TYPE
	 SYNTAX    INTEGER
         ACCESS    read-only
         STATUS    mandatory
         DESCRIPTION
                 "Real size of Slots Table in the Stack."
		 ::= { nbsStackInfo 2 }

	 nbsStackPortsCapacity		OBJECT-TYPE
	 SYNTAX    INTEGER
         ACCESS    read-only
         STATUS    mandatory
         DESCRIPTION
                 "Max quantity of Ports possible in the Stack ."
	 ::= { nbsStackInfo 3 }

	 nbsStackSlotPortsCapacity	OBJECT-TYPE
	 SYNTAX    INTEGER
         ACCESS    read-only
         STATUS    mandatory
         DESCRIPTION
                 "Max quantity of Ports possible in the Slot ."
	 ::= { nbsStackInfo 4 }

-- *************************************************************
-- Objects in the Slot Information Group
-- *************************************************************
        
	 nbsStackSlotTable OBJECT-TYPE
	 SYNTAX    SEQUENCE OF NbsStackSlotEntry
         ACCESS    not-accessible
         STATUS    mandatory
         DESCRIPTION
                 "Table of descriptive and status information about
	          the Slots."
		 ::= { nbsStackInfo 5 }

	 nbsStackSlotEntry OBJECT-TYPE
	 SYNTAX    NbsStackSlotEntry
         ACCESS    not-accessible
         STATUS    mandatory
         DESCRIPTION
                 "An entry in the table, containing information
                  about a single Slot."
	 INDEX   { nbsStackSlotIndex }
		 ::= { nbsStackSlotTable 1 }

	 NbsStackSlotEntry ::=
	 SEQUENCE   {
		     nbsStackSlotIndex
                          INTEGER,
		     nbsStackSlotType
                          INTEGER,                         
		     nbsStackSlotMgmtStatus
                          INTEGER,
		     nbsStackSlotPortsMaxNumber
                          INTEGER,
		     nbsStackSlotPortsNumber
                          INTEGER,
		     nbsStackSlotFirstPort
                          INTEGER,
		     nbsStackSlotOperStatus
                          INTEGER,
		     nbsStackSlotAdminStatus
                          INTEGER,
		     nbsStackSlotRedundantPSMode
                          INTEGER,
		     nbsStackSlotUplinkModulesNumber
			  INTEGER,
		     nbsStackSlotReset
                          INTEGER,
		     nbsStackSlotIp
                          IpAddress,
		     nbsStackSlotHwVers
			  INTEGER,
		     nbsStackSlotSwVers
			  INTEGER
		    }

	 nbsStackSlotIndex	 OBJECT-TYPE
         SYNTAX    INTEGER
         ACCESS    read-only
         STATUS    mandatory
         DESCRIPTION
		 "This object identifies the Slot#
		  for which this entry contains information."
		 ::= { nbsStackSlotEntry 1 }
       
	 nbsStackSlotType          OBJECT-TYPE
         SYNTAX    INTEGER
         ACCESS    read-only
         STATUS    mandatory
         DESCRIPTION
         "Slot Types:
	    1=empty - Slot is Empty;
	    2=unknown - Slot is of the Unknown type;
	    3=standAlone - Stand Alone Device;
	    4=universal - Slot including Uplink Modules of the different types;
	    5=eth20Ports10or100TP - Slot including 20 fast   copper 10/100 MBps Ports;
	    6=eth40Ports10TP - Slot including 40 normal copper 10 MBps Ports;
	    7=eth10Ports100FO - Slot including 10 fast fibre optic 100 MBps Ports(Multi Mode);
	    8=eth16Ports10or100TP - Slot including 16 fast   copper 10/100 MBps Ports;
	    9=eth4Ports1000FO - Slot including  4 GigaBit 1000 MBps Ports(Multi Mode);
	   10=agentSlot - Slot including  CPU  Card;
	   11=routingEngine - Slot including  Routing Engine Card;
	   12=eth8Ports10or100TP - Slot including  8 fast   copper 10/100 MBps Ports;
	   13=eth2Ports100FOMM - Slot including  2 fast fibre optic 100 MBps Ports(MM=Multi  Mode);
	   14=eth2Ports100FOSM - Slot including  2 fast fibre optic 100 MBps Ports(SM=Single Mode);
	   15=eth1Ports1000FOMM - Slot including  1 GigaBit 1000 MBps Ports(MM=Multi  Mode);
	   16=eth1Ports1000FOSM - Slot including  1 GigaBit 1000 MBps Ports(SM=Single Mode);
	   17=eth2Ports1000FOMM - Slot including  2 GigaBit 1000 MBps Ports(MM=Multi  Mode);
	   18=eth2Ports1000FOSM - Slot including  2 GigaBit 1000 MBps Ports(SM=Single Mode);
	   19=stackableSlotNoLink - Slot including special Stackable Card with no Link;
	   20=stackableSlotNH2025 - Slot including special Stackable Card Linked with the NH2025 Device;
	   21=stackableSlotReserve1 - Slot including special Stackable Card (Reserve1 for the future purposes);
	   22=stackableSlotReserve2 - Slot including special Stackable Card (Reserve2 for the future purposes);
	   23=eth2Ports100FO - Slot including  2 fast fibre optic 100 MBps Ports(different configuration of the Multi Mode and/or Single Mode Ports);
	   24=eth2Ports1000FO - Slot including  2 GigaBit 1000 MBps Ports(different configuration of the Multi Mode and/or Single Mode Ports);
	   25=eth4Ports100FOMM - Slot including  4 fast fibre optic 100 MBps Ports(MM=Multi  Mode);
	   26=eth4Ports100FOSM - Slot including  4 fast fibre optic 100 MBps Ports(SS=Single Mode);
	   27=eth4Ports100FO - Slot including  4 fast fibre optic 100 MBps Ports(different configuration of the Multi Mode and/or Single Mode Ports);
	   28=eth4Ports10or100TP - Slot including  4 fast copper   10/100 MBps Ports;
	   29=eth4Ports100MTRJ - Slot including  4 fast fibre optic 100 MBps MTRJ Ports;
	   30=eth8Ports100MTRJ - Slot including  8 fast fibre optic 100 MBps MTRJ Ports;
	   31=eth4Ports100VF - Slot including  4 fast fibre optic 100 MBps VF Ports;
	   32=eth8Ports100VF - Slot including  8 fast fibre optic 100 MBps VF Ports;
	   33=ethGigaBitService - Slot including special Giga Bit Service Card (for using Modules with >= 2 GigaBit Ports);
	   34=eth4Ports100LC - Slot including  4 fast fibre optic 100 MBps LC Ports;
	   35=eth8Ports100LC - Slot including  8 fast fibre optic 100 MBps LC Ports;
	   36=eth2Ports10FL - Slot including  2 slow fibre optic 10  MBps FL Ports;
	   37=eth4Ports10FL - Slot including  4 slow fibre optic 10  MBps FL Ports;
	   38=eth1Port100or1000TP - Slot including  1 GigaBit copper   100/1000 MBps TP Ports;
	   39=eth1Port1000FORED - Slot including 1 GigaBit fibre optic Redundant Port;
	   40=eth4Ports100TPand2Ports100FO - Slot including 4 copper 10/100 MBps TP + 2 fast FO 100 MBps Ports;
	   41=eth4Ports100TPand1Port100FO - Slot including 4 copper 10/100 MBps TP + 1 fast FO 100 MBps Ports;
	   42=eth0Ports100TPand2Ports100FO - Slot including 0 copper 10/100 MBps TP + 2 fast FO 100 MBps Ports;
	   43=eth4Ports100TPand0Ports100FO - Slot including 4 copper 10/100 MBps TP + 0 fast FO 100 MBps Ports;
	   44=eth1Ports1000MTRJ - Slot including 1 GigaBit MTRJ fibre optic     1000 MBps Port;
	   45=eth1StackPorts100or1000TP - Slot including 1 GigaBit TP copper 100/1000 MBps Port for Low Distances(<= 5m);
	   46=eth2PseudoMgmt10or100TP - Slot including 2 copper 10/100 MBps TP for the Pseudo Management purpouses;
	   47=eth4Ports10HPNA - Slot including 4 slow Home PNA 10 MBps half duplex Ports;
	   48=eth8Ports10HPNA - Slot including 8 slow Home PNA 10 MBps half duplex Ports;
	   49=eth1Port1000AMP - Slot including 1 GigaBit copper 1000 MBps AMP Ports;
	   50=l3eth1Ports1000FO - Slot including 1 GigaBit 1000 MBps Ports with Layer3 features support;
	   51=l3eth8Ports10or100TP - Slot including 8 fast   copper 10/100 MBps Ports with Layer3 features support;
	   52=l3eth4Ports100TPand1Port100FO - Slot including 4 copper 10/100 MBps TP + 1 fast FO 100 MBps Ports with Layer3 features support;
	   53=l3eth8Ports100MTRJ - Slot including 8 fast fibre optic 100 MBps MTRJ Ports with Layer3  featuressupport;
	   54=l3eth4Ports100LC - Slot including 4 fast fibre optic 100 MBps LC Ports with Layer3 features support;
	   55=l3eth8Ports100LC - Slot including 8 fast fibre optic 100 MBps LC Ports with Layer3 features support;
	   56=l3eth2Ports10FL - Slot including 2 slow fibre optic 10  MBps FL Ports with Layer3 features support;
	   57=l3eth4Ports10FL - Slot including 4 slow fibre optic 10  MBps FL Ports with Layer3 features support;
	   58=l3eth4Ports100MTRJ - Slot including 4 fast fibre optic 100 MBps MTRJ Ports with Layer3 features support;
	   59=l3eth0Ports100TPand2Ports100FO - Slot including 0 copper 10/100 MBps TP + 2 fast FO 100 MBps Ports with Layer3 features support;
	   60=l3eth2Ports1000FO - Slot including 2 GigaBit 1000 MBps Ports(different configuration of the Multi Mod and/or Single Mode Ports) with Layer3 features support;
	   61=l3eth4Ports100FO - Slot including 4 fast fibre optic 100 MBps Ports(different configuration of the Multi Mode and/or Single Mode Ports) with Layer3 features support;
	   62=l3eth4Ports100TPand0Ports100FO - Slot including 4 copper 10/100 MBps TP + 0 fast FO 100 MBps Ports with Layer3 features support;
	   63=l3eth4Ports100VF - Slot including 4 fast fibre optic 100 MBps VF Ports with Layer3 features support;
	   64=l3eth8Ports100VF - Slot including 8 fast fibre optic 100 MBps VF Ports with Layer3 features support;
	   65=l3eth4Ports100TPand2Ports100FO - Slot including 4 copper 10/100 MBps TP + 2 fast FO 100 MBps Ports with Layer3 features support;
	   66=l3eth1Port100or1000TP - Slot including 1 GigaBit copper   100/1000 MBps TP Ports with Layer3 support;
	   67=l3eth1Port1000FORED - Slot including 1 GigaBit fibre optic Redundant Port with Layer3 features support;
	   68=l3eth1Ports1000MTRJ - Slot including 1 GigaBit MTRJ fibre optic 1000 MBps Port  with Layer3 features support;
	   69=l3eth1Port1000AMP - Slot including 1 GigaBit copper 1000 MBps AMP Ports with Layer3 features support with Layer3 features support;
	   70=l3eth4Ports10HPNA - Slot including 4 slow Home PNA 10 MBps half duplex Ports with Layer3 features support;
	   71=l3eth8Ports10HPNA - Slot including 8 slow Home PNA 10 MBps half duplex Ports with Layer3 features support;
	   72=l3eth2Ports10or100RC - Slot including 2 copper 10/100 MBps TP for the Pseudo Management purpouses;
	   73=eth2Ports1000FOSM50Mcam16 - Slot including 2 GigaBit 1000 MBps Ports(SM=Single Mode);
	   74=eth2Ports1000FOSM50Mcam32 - Slot including 2 GigaBit 1000 MBps Ports(SM=Single Mode);
	   75=eth1Ports1000FOSM50Mcam16 - Slot including 1 GigaBit 1000 MBps Ports(SM=Single Mode);
	   76=eth1Ports1000FOSM50Mcam32 - Slot including 1 GigaBit 1000 MBps Ports(SM=Single Mode);
          
	   77=eth2Ports1000FOSM100Mcam16 - Slot including 2 GigaBit 1000 MBps Ports(SM=Single Mode);
	   78=eth2Ports1000FOSM100Mcam32 - Slot including 2 GigaBit 1000 MBps Ports(SM=Single Mode);
	   79=eth1Ports1000FOSM100Mcam16 - Slot including 1 GigaBit 1000 MBps Ports(SM=Single Mode);
	   80=eth1Ports1000FOSM100Mcam32 - Slot including 1 GigaBit 1000 MBps Ports(SM=Single Mode);
           81=eth8singlePortsEoVL - Slot including 8 Ethernet over Single VDSL LT Ports;
           82=eth8singlePortsEoVN - Slot including 8 Ethernet over Single VDSL NT Ports;
           83=eth8singlePortsLEoVL - Slot including 8 Ethernet over Single VDSL LongReach LT Ports;
           84=eth8singlePortsLEoVN - Slot including 8 Ethernet over Single VDSL LongReach NT Ports;
           85=eth4PortsEoVand2Ports100FO - Slot including 4 Ethernet over VDSL LT Ports + 2 fast FO 100 MBps Ports;
           86=eth4PortsEoVand2Ports10or100TP - Slot including 4 Ethernet over VDSL LT Ports + 2 Copper 10/100 MBps Ports;
           87=eth4singlePortsEoVL4PortsEoVN - Slot including 4 Ethernet over Single VDSL LT Ports + 4 Ethernet over Single VDSL NT Ports;
           88=eth2Ports100FOPAL - Slot including 2 fast fibre optic 100 MBps PassiveAirLink(PAL) Ports;
           89=eth4PortsEoVand1Ports100FO - Slot including 4 Ethernet over VDSL LT Ports + 1 fast FO 100 MBps Ports;
           90=eth4PortsEoVand1Ports10or100TP - Slot including 4 Ethernet over VDSL LT Ports + 1 Copper 10/100 MBps Ports;
           91=eth4PortsEoVand1Ports10or100TPand1Ports100FO - Slot including 4 Ethernet over VDSL LT Ports + 1 Copper 10/100 MBps Ports + 1 fast FO 100 MBps Ports;
           92=l3eth8octalPortsEoVL - Slot including 8 Ethernet over Octal VDSL LT Ports with Layer3 features support;

           93=l3eth1Port1000GBICSFP - Slot including 1 GigaBit 1000 MBps Port with GBIC and SFP connectors;
           94=l3eth2Ports100FOPAL - Slot including 2 fast fibre optic 100 MBps PassiveAirLink(PAL) Ports with Layer3 features support;
           95=eth8octalPortsEoVSL - Slot including 8 Ethernet over Octal VDSL smart-phone compliant LT Ports;
           96=l3eth8octalPortsEoVSL - Slot including 8 Ethernet over Octal VDSL smart-phone compliant LT Ports with Layer3 features support;
           97=eth8octalPortsEoV7L - Slot including 8 Ethernet over Octal VDSL ETSI 997 compliant LT Ports;
           98=l3eth8octalPortsEoV7L - Slot including 8 Ethernet over Octal VDSL ETSI 997 compliant LT Ports with Layer3 features support;
           99=l3eth8PortVoice - Slot including 8 E1\T1 voice ports with Layer3 features support;
          100=l3eth4PortVoice - Slot including 4 E1\T1 voice ports with Layer3 features support;
          101=l3eth2PortVoiceand2PortsTPand1PortFO - Slot including 2 E1\T1 voice ports + 2 Copper 10/100 MBps Ports + 1 fast FO 100 MBps Port with Layer3 features support;
	  102=eth4Ports100TPand1PortSingleFO - Slot including 4 copper 10/100 MBps TP + 1 fast Single FO 100 MBps Ports;
	  103=l3eth4Ports100TPand1PortSingleFO - Slot including 4 copper 10/100 MBps TP + 1 fast Single FO 100 MBps Ports with Layer3 features support;
          104=eth8octalPortsEoVL - Slot including 8 Ethernet over Octal VDSL LT Ports;
          105=eth8singlePortsEoVED - Slot including 8 Ethernet over Single VDSL Extended Distanse LT Ports;
          106=eth8singlePortsEoV4B - Slot including 8 Ethernet over 4 band Single VDSL LT Ports;

          107=l3eth1Port1000SFP    - Slot including 1 GigaBit 1000 MBps Port with SFP connector [OS Devices];
	  108=eth1Port1000GERcam32 - Slot including 1 GigaBit Redundant Port with cam=32 [OSM Devices];
	  109=eth1Port1000GERcam256- Slot including 1 GigaBit Redundant Port with cam>32 [OSM Devices];
	  110=eth1Port1000GERSFPcam32 - Slot including 1 GigaBit Redundant Port with SFP connectors and cam=32 [OSM Devices];
	  111=eth1Port1000GERSFPcam256- Slot including 1 GigaBit Redundant Port with SFP connectors and cam>32 [OSM Devices];
          112=eth1Port1000SFPcam32 - Slot including 1 GigaBit 1000 MBps Port with SFP connector and cam=32 [OSM Devices];
          113=eth1Port1000SFPcam256- Slot including 1 GigaBit 1000 MBps Port with SFP connector and cam>32 [OSM Devices];
          114=eth6Ports100TPand2Ports100FO - Slot including 6 copper 10/100 MBps TP + 2 fast FO 100 MBps Ports;

          115=em2007eth1Port1000SFPcam32 - Slot including 1 GigaBit 1000 MBps Port with SFP connector and cam=32 [OSM207 Device];
	  116=em2007eth1Port1000SFPcam256- Slot including 1 GigaBit 1000 MBps Port with SFP connector and cam>32 [OSM207 Device];
	  117=em2007eth8Ports10or100TP   - Slot including 8 fast copper 10/100 MBps Ports [OSM207 Device];
	  118=em2007eth8Ports100MTRJ     - Slot including 8 fast fibre optic 100 MBps MTRJ Ports [OSM207 Device];
	  119=em2007eth1Port1000GERSFPcam32 - Slot including 1 GigaBit Redundant Port with SFP connectors and cam=32 [OSM207 Device];

          120=eth6Ports100TPand1Ports100FO - Slot including 6 copper 10/100 MBps TP + 1 fast FO 100 MBps Ports;"
		 ::= { nbsStackSlotEntry 2 }

	 nbsStackSlotMgmtStatus        OBJECT-TYPE
         SYNTAX    INTEGER {
		       master(1),
		       slave(2)
                      }
	 ACCESS    read-only
	 STATUS    mandatory
         DESCRIPTION
                 "Slot Module Management Status:
				  master            - Master Slot Module;
				  slave             - Slave  Slot Module."
		 ::= { nbsStackSlotEntry 3 }

	 nbsStackSlotPortsMaxNumber  OBJECT-TYPE
         SYNTAX    INTEGER 
         ACCESS    read-only
         STATUS    mandatory
         DESCRIPTION
		 "This object identifies the Maximum possible Ports Number in the Slot."
		 ::= { nbsStackSlotEntry 4 }
       
	 nbsStackSlotPortsNumber   OBJECT-TYPE
         SYNTAX    INTEGER 
         ACCESS    read-only
         STATUS    mandatory
         DESCRIPTION
		 "This object identifies the Real Ports Number in the Slot."
		 ::= { nbsStackSlotEntry 5 }
       
	 nbsStackSlotFirstPort     OBJECT-TYPE
         SYNTAX    INTEGER
         ACCESS    read-only
         STATUS    mandatory
         DESCRIPTION
		 "This object identifies the number of the First Port
		  in the Slot, according to the Stack Ports Numeration."
		 ::= { nbsStackSlotEntry 6 }
       
	 nbsStackSlotOperStatus    OBJECT-TYPE
         SYNTAX    INTEGER {
		       switchedOff(1),
		       enabled(2),
		       disabled(3),
		       changing(4)
                      }
         ACCESS    read-only
         STATUS    mandatory
         DESCRIPTION
                 "Slot Oper Status:
				  switchedOff      - Slot is Switched-off;
				  enabled          - Slot is enabled;
				  disabled         - Slot is disabled;
				  changing         - Slot is changing."
		 ::= { nbsStackSlotEntry 7 }

	 nbsStackSlotAdminStatus   OBJECT-TYPE
         SYNTAX    INTEGER {
		       enabled(1),
		       disabled(2)
                      }
         ACCESS    read-write
         STATUS    mandatory
         DESCRIPTION
                 "Slot Admin Status:
				  enabled           - Slot is enabled;
				  disabled          - Slot is disabled."
		 ::= { nbsStackSlotEntry 8 }

	 nbsStackSlotRedundantPSMode OBJECT-TYPE
         SYNTAX    INTEGER {
		       notConnected(1),
		       connected(2)
		      }
         ACCESS    read-only
         STATUS    mandatory
         DESCRIPTION
				 "Slot Redundant Power Supply Module Status:
				  notConnected     - Redundant Power Supply is not Existing;
				  connected        - Redundant Power Supply is Existing."
		 ::= { nbsStackSlotEntry 9 }

	 nbsStackSlotUplinkModulesNumber OBJECT-TYPE
	 SYNTAX    INTEGER
         ACCESS    read-only
         STATUS    mandatory
         DESCRIPTION
				 "This object identifies the number of the Uplink Modules
                  in the Slot."
		 ::= { nbsStackSlotEntry 10 }
       
	 nbsStackSlotReset         OBJECT-TYPE
	 SYNTAX    INTEGER {
	       running(1),
               reset(2)
		      }
         ACCESS    read-write
         STATUS    mandatory
         DESCRIPTION
		 "This object is used to reset the corresponding Slot Module."
		 ::= { nbsStackSlotEntry 11 }

	 nbsStackSlotIp         OBJECT-TYPE
	 SYNTAX    IpAddress
		ACCESS    read-only
		STATUS    mandatory
		DESCRIPTION
		 "Ip address of the slot (if it has it; if it hasn't - 0.0.0.0)."
		 ::= { nbsStackSlotEntry 12 }

	 nbsStackSlotHwVers     OBJECT-TYPE
	 SYNTAX  INTEGER
	 ACCESS  read-only
         STATUS  mandatory
		DESCRIPTION
		"This object holds the Software Version of the Slot Module."
		 ::= { nbsStackSlotEntry 13 }

	 nbsStackSlotSwVers     OBJECT-TYPE
	 SYNTAX  INTEGER
	 ACCESS  read-only
         STATUS  mandatory
		DESCRIPTION
		"This object holds the Hardware Version of the Slot Module."
		 ::= { nbsStackSlotEntry 14 }

-- *************************************************************
-- Objects in the Uplink Information Group
-- *************************************************************
        
	 nbsStackSlotUplTable   OBJECT-TYPE
	 SYNTAX  SEQUENCE OF NbsStackSlotUplEntry
         ACCESS  not-accessible
         STATUS  mandatory
         DESCRIPTION
                 "A table of Uplink Modules mounted on the corresponding Slot of the Switch."		
		 ::= { nbsStackInfo 6 }

	 nbsStackSlotUplEntry   OBJECT-TYPE
	 SYNTAX  NbsStackSlotUplEntry
         ACCESS  not-accessible
         STATUS  mandatory
         DESCRIPTION
		"Contains the information needed to identify the Uplink Module of the Slot."
	 INDEX { nbsStackSlotNumber,
		 nbsStackSlotUplNumber }
		::= { nbsStackSlotUplTable 1 }

	 NbsStackSlotUplEntry ::=
	 SEQUENCE   {
		     nbsStackSlotNumber
                          INTEGER,
		     nbsStackSlotUplNumber
			  INTEGER,
		     nbsStackSlotUplType
                          INTEGER,
		     nbsStackSlotUplSwVers
                          INTEGER,
		     nbsStackSlotUplHwVers
                          INTEGER,
		     nbsStackSlotUplNPorts
                          INTEGER,
		     nbsStackSlotUplFirstPort
                          INTEGER,
		     nbsStackSlotUplPortsMask
			  PortsBitmap,
		     nbsStackSlotUplStatus
                          INTEGER,
		     nbsStackSlotUplHwDescr
	         	  DisplayString,
		     nbsStackSlotUplSwDescr
    	     		  DisplayString
		    }

	 nbsStackSlotNumber        OBJECT-TYPE
	 SYNTAX  INTEGER
         ACCESS  read-only
         STATUS  mandatory
         DESCRIPTION
		 "The Slot # in the Device."
		 ::= { nbsStackSlotUplEntry 1 }

	 nbsStackSlotUplNumber     OBJECT-TYPE
	 SYNTAX  INTEGER
         ACCESS  read-only
         STATUS  mandatory
         DESCRIPTION
		 "The Uplink Module # in the
		  corresponding Slot in the Device."
		 ::= { nbsStackSlotUplEntry 2 }

	 nbsStackSlotUplType       OBJECT-TYPE
	 SYNTAX  INTEGER
         ACCESS    read-only
	 STATUS    mandatory
         DESCRIPTION
                 "Uplink Module Types:
                    1=uplAbsent - Uplink Module is Absent;
                    2=uplUnknown - Uplink Module of the Unknown type;
                    3=upl1GigaMM - Uplink Module including 1 GigaBit 1000 MBps Ports(MM=Multi  Mode);
                    4=upl1GigaSM - Uplink Module including 1 GigaBit 1000 MBps Ports(SM=Single Mode);
                    5=upl2GigaMM - Uplink Module including 2 GigaBit 1000 MBps Ports(MM=Multi  Mode);
                    6=upl2GigaSM - Uplink Module including 2 GigaBit 1000 MBps Ports(SM=Single Mode);
                    7=upl1FO - Uplink Module including 1 fast fibre optic 100 MBps Ports;
                    8=upl1TP - Uplink Module including 1 fast copper   10/100 MBps Ports;
                    9=upl2FOMM - Uplink Module including 2 fast fibre optic 100 MBps Ports(MM=Multi  Mode);
                   10=upl2FOSM - Uplink Module including 2 fast fibre optic 100 MBps Ports(SM=Single Mode);
                   11=upl4FOMM - Uplink Module including 4 fast fibre optic 100 MBps Ports(MM=Multi  Mode);
                   12=upl4FOSM - Uplink Module including 4 fast fibre optic 100 MBps Ports(SM=Single Mode);
                   13=upl8TP - Uplink Module including 8 fast copper   10/100 MBps Ports;
                   14=upl1ATM - Uplink Module including 1 ATM Port;
                   15=upl1FDDI - Uplink Module including 1 FDDI Port;
                   16=uplStackModuleNoLink - special Stacking Module with no Link;
                   17=uplStackModuleNH2025 - special Stacking Module Linked with the NH2025 Device;
                   18=uplStackModuleReserve1 - special Stacking Module (Reserve1 for the future purposes);
                   19=uplStackModuleReserve2 - special Stacking Module (Reserve2 for the future purposes);
                   20=upl4TP - Uplink Module including 4 fast copper   10/100 MBps Ports;
                   21=upl2FO - Uplink Module including 2 fast fibre optic 100 MBps Ports(different configuration of the Multi Mode and/or Single Mode Ports);
                   22=upl2Giga - Uplink Module including 2 GigaBit 1000 MBps Ports(different configuration of the Multi Mode and/or Single Mode Ports);
                   23=upl4FO - Uplink Module including 4 fast fibre optic 100 MBps Ports(different configuration of the Multi Mode and/or Single Mode Ports);
                   24=upl4MTRJ - Uplink Module including 4 fast fibre optic 100 MBps MTRJ Ports;
                   25=upl8MTRJ - Uplink Module including 8 fast fibre optic 100 MBps MTRJ Ports;
                   26=upl4VF - Uplink Module including 4 fast fibre optic 100 MBps VF Ports;
                   27=upl8VF - Uplink Module including 8 fast fibre optic 100 MBps VF Ports;
                   28=upl4LC - Uplink Module including 4 fast fibre optic 100 MBps LC Ports;
                   29=upl8LC - Uplink Module including 8 fast fibre optic 100 MBps LC Ports;
                   30=upl2FL - Uplink Module including 2 slow fibre optic 10  MBps FL Ports;
                   31=upl4FL - Uplink Module including 4 slow fibre optic 10  MBps FL Ports;
                   32=upl1GigaTP - Uplink Module including 1 GigaBit copper   100/1000 MBps TP Ports;
                   33=upl1GER - Uplink Module including 1 GigaBit fibre optic Redundant Port;
                   34=upl4TP2FO - Uplink Module including 4 copper 10/100 MBps TP + 2 fast FO 100 MBps Ports;
                   35=upl4TP1FO - Uplink Module including 4 copper 10/100 MBps TP + 1 fast FO 100 MBps Ports;
                   36=upl0TP2FO - Uplink Module including 0 copper 10/100 MBps TP + 2 fast FO 100 MBps Ports;
                   37=upl4TP0FO - Uplink Module including 4 copper 10/100 MBps TP + 0 fast FO 100 MBps Ports;
                   38=upl1GigaMTRJ - Uplink Module including 1 GigaBit MTRJ fibre optic     1000 MBps Port;
                   39=upl1GigaStackTP - Uplink Module including 1 GigaBit TP copper 1000 MBps Port for Low Distances(<= 5m);
                   40=upl4Ports10HPNA - Uplink Module including 4 slow Home PNA 10 MBps half duplex Ports;
                   41=upl8Ports10HPNA - Uplink Module including 8 slow Home PNA 10 MBps half duplex Ports;
                   42=upl1Port1000AMP - Uplink Module including 1 GigaBit copper 1000 MBps AMP Ports;
                   43=l3upl1Giga1000 - Uplink Module including 1 GigaBit 1000 MBps Ports with Layer3 features support;
                   44=l3upl8TP - Uplink Module including 8 fast copper   10/100 MBps Ports with Layer3 features support;
                   45=l3upl4TP1FO - Uplink Module including 4 copper 10/100 MBps TP + 1 fast FO 100 MBps Ports with Layer3 features support;
                   46=l3upl8MTRJ - Uplink Module including 8 fast fibre optic 100 MBps MTRJ Ports with Layer3 features support;
                   47=l3upl4LC - Uplink Module including 4 fast fibre optic 100 MBps LC Ports with Layer3 features support;
                   48=l3upl8LC - Uplink Module including 8 fast fibre optic 100 MBps LC Ports with Layer3 features support;
                   49=l3upl2FL - Uplink Module including 2 slow fibre optic 10  MBps FL Ports with Layer3 features support;
                   50=l3upl4FL - Uplink Module including 4 slow fibre optic 10  MBps FL Ports with Layer3 features support;
                   51=l3upl4MTRJ - Uplink Module including 4 fast fibre optic 100 MBps MTRJ Ports with Layer3 features support;
                   52=l3upl0TP2FO- Uplink Module including 0 copper 10/100 MBps TP + 2 fast FO 100 MBps Ports with Layer3 features support;
                   53=l3upl2Giga - Uplink Module including 2 GigaBit 1000 MBps Ports(different configuration of the Multi Mode and/or Single Mode Ports) with Layer3 features support;
                   54=l3upl4FO - Uplink Module including 4 fast fibre optic 100 MBps Ports(different configuration of the Multi Mode and/or Single Mode Ports) with Layer3 features support;
                   55=l3upl4TP0FO- Uplink Module including 4 copper 10/100 MBps TP + 0 fast FO 100 MBps Ports with Layer3 features support;
                   56=l3upl4VF - Uplink Module including 4 fast fibre optic 100 MBps VF Ports with Layer3 features support;
                   57=l3upl8VF - Uplink Module including 8 fast fibre optic 100 MBps VF Ports with Layer3 features support;
                   58=l3upl4TP2FO- Uplink Module including 4 copper 10/100 MBps TP + 2 fast FO 100 MBps Ports with Layer3 features support;
                   59=l3upl1Giga100or1000- Uplink Module including 1 GigaBit copper   100/1000 MBps TP Ports with Layer3 features support;
                   60=l3upl1GER - Uplink Module including 1 GigaBit fibre optic Redundant Port with Layer3 features support;
                   61=l3upl1GigaMTRJ - Uplink Module including 1 GigaBit MTRJ fibre optic     1000 MBps Port with Layer3 features support;
                   62=l3upl1Port1000AMP - Uplink Module including 1 GigaBit copper 1000 MBps AMP Ports with Layer3 features support;
                   63=l3upl4Ports10HPNA - Uplink Module including 4 slow Home PNA 10 MBps half duplex Ports with Layer3 features support;
                   64=l3upl8Ports10HPNA - Uplink Module including 8 slow Home PNA 10 MBps half duplex Ports with Layer3 features support;
                   65=upl8singlePortsEoVL - Uplink Module including 8 Ethernet over Single VDSL LT Ports;
                   66=upl8singlePortsEoVN - Uplink Module including 8 Ethernet over Single VDSL NT Ports;
                   67=upl8singlePortsLEoVL- Uplink Module including 8 Ethernet over Single VDSL LongReach LT Ports;
                   68=upl8singlePortsLEoVN- Uplink Module including 8 Ethernet over Single VDSL LongReach NT Ports;
                   69=upl4PortsEoVand2FO - Uplink Module including 8 Ethernet over VDSL LT Ports + 2 fast FO 100 MBps Ports;
                   70=upl4PortsEoVand2TP - Uplink Module including 8 Ethernet over VDSL LT Ports + 2 Copper 10/100 MBps Ports;
                   71=upl4singlePortsEoVL4PortsEoVN - Uplink Module including 4 Ethernet over Single VDSL LT Ports + 4 Ethernet over VDSL NT Ports;
                   72=upl2Ports100FOPAL - Uplink Module including 2 fast fibre optic 100 MBps PassiveAirLink(PAL) Ports;
                   73=upl4PortsEoVand1Ports100FO - Uplink Module including 4 Ethernet over VDSL LT Ports + 1 fast FO 100 MBps Ports;
                   74=upl4PortsEoVand1Ports10or100TP - Uplink Module including 4 Ethernet over VDSL LT Ports + 1 Copper 10/100 MBps Ports;
                   75=upl4PortsEoVand1Ports10or100TPand1Ports100FO - Uplink Module including 4 Ethernet over VDSL LT Ports + 1 Copper 10/100 MBps Ports + 1 fast FO 100 MBps Ports;
                   76=l3upl8octalPortsEoVL - Uplink Module including 8 Ethernet over Octal VDSL LT Ports with Layer3 features support;

                   77=l3upl1Port1000GBICSFP - Uplink Module including 1 GigaBit 1000 MBps Port with GBIC and SFP connectors;
                   78=l3upl2Ports100FOPAL  - Uplink Module including 2 fast fibre optic 100 MBps PassiveAirLink(PAL) Ports with Layer3 features support;
                   79=upl8octalPortsEoVSL - Uplink Module including 8 Ethernet over Octal VDSL smart-phone compliant LT Ports;
                   80=upl8octalPortsEoV7L - Uplink Module including 8 Ethernet over Octal VDSL smart-phone compliant LT Ports with Layer3 features support;
                   81=upl8octalPrtEoV7L - Uplink Module including 8 Ethernet over Octal VDSL ETSI 997 compliant LT Ports;
                   82=l3upl8octalPortsEoV7L - Uplink Module including 8 Ethernet over Octal VDSL ETSI 997 compliant LT Ports with Layer3 features support;
                   83=l3upl8PortVoice - Uplink Module including 8 E1\T1 voice ports with Layer3 features support;
                   84=l3upl4PortVoice - Uplink Module including 4 E1\T1 voice ports with Layer3 features support;
                   85=l3upl2PortVoiceand2PortsTPand1PortFO - Uplink Module including 2 E1\T1 voice ports + 2 Copper 10/100 MBps Ports + 1 fast FO 100 MBps Port with Layer3 features support;
                   86=upl4TP1SingleFO - Uplink Module including 4 copper 10/100 MBps TP + 1 fast Single FO 100 MBps Ports;
                   87=l3upl4TP1SingleFO - Uplink Module including 4 copper 10/100 MBps TP + 1 fast Single FO 100 MBps Ports with Layer3 features support;
                   88=upl8octalPortsEoVL - Uplink Module including 8 Ethernet over Octal VDSL LT Ports;
                   89=upl8singlePortsEoVED - Uplink Module including 8 Ethernet over Single VDSL Extended Distanse LT Ports;
                   90=upl8singlePortsEoV4B - Uplink Module including 8 Ethernet over 4 band Single VDSL LT Ports;"
		 ::= { nbsStackSlotUplEntry 3 }

	 nbsStackSlotUplSwVers     OBJECT-TYPE
	 SYNTAX  INTEGER
	 ACCESS  read-only
         STATUS  mandatory
         DESCRIPTION
		 "This object holds the Software Version of the Uplink Module."
		 ::= { nbsStackSlotUplEntry 4 }

	 nbsStackSlotUplHwVers     OBJECT-TYPE
	 SYNTAX  INTEGER
         ACCESS  read-only
         STATUS  mandatory
         DESCRIPTION
		 "This object holds the Hardware Version of the Uplink Module."
		 ::= { nbsStackSlotUplEntry 5 }

	 nbsStackSlotUplNPorts     OBJECT-TYPE
	 SYNTAX  INTEGER
         ACCESS  read-only
         STATUS  mandatory
         DESCRIPTION
		 "Number of Ports in the current UpLink Module."
		 ::= { nbsStackSlotUplEntry 6 }

	 nbsStackSlotUplFirstPort  OBJECT-TYPE
         SYNTAX    INTEGER
         ACCESS    read-only
         STATUS    mandatory
         DESCRIPTION
		 "This object identifies the number of the First Port
                  in the Uplink Module, according to the Stack Ports Numeration."
		 ::= { nbsStackSlotUplEntry 7 }
       

	 nbsStackSlotUplPortsMask  OBJECT-TYPE
	 SYNTAX  PortsBitmap
	 ACCESS  read-only
         STATUS  mandatory
         DESCRIPTION
		 "Contains the list of the ports in the Uplink Module.
                  The representation is a bit map.
                  Each octet within the value of this object specifies
                  a set of eight ports, with the first octet specifying
                  ports 1 through 8, the second octet specifying ports 9
                  through 16, etc.  Within each octet, the least
                  significant bit represents the lowest numbered
				  port, and the most significant bit represents the
                  highest numbered port.  Thus, each port of the
				  Uplink Module is represented by a single bit within the
                  value of this object.  If that bit has a value of
				  <1> then that port is exists in the Uplink Module.
				  The port is not exists if its bit has a value of <0>."

		 ::= { nbsStackSlotUplEntry 8 }

	 nbsStackSlotUplStatus     OBJECT-TYPE
	 SYNTAX    INTEGER {             
		       up(1),
                       down(2)
		      }
         ACCESS    read-only
         STATUS    mandatory
         DESCRIPTION
		 "Current status of the Uplink Module"
		 ::= { nbsStackSlotUplEntry 9 }

	 nbsStackSlotUplHwDescr     OBJECT-TYPE
        SYNTAX  DisplayString
        ACCESS  read-only
        STATUS  mandatory
		DESCRIPTION
		"A description of the Hardware Version of the Uplink Module."
		 ::= { nbsStackSlotUplEntry 10 }

	 nbsStackSlotUplSwDescr     OBJECT-TYPE
        SYNTAX  DisplayString
        ACCESS  read-only
        STATUS  mandatory
		DESCRIPTION
		"A description of the Software Version of the Uplink Module."
		 ::= { nbsStackSlotUplEntry 11 }

-- *************************************************************
-- Objects in the Special Slot Table (GigaBit Redundant Modules)
-- *************************************************************
        
	 nbsStackSpecSlotTable OBJECT-TYPE
	 SYNTAX    SEQUENCE OF NbsStackSpecSlotEntry
         ACCESS    not-accessible
         STATUS    mandatory
         DESCRIPTION
                 "Table of descriptive and status information about
	          the Special Slots."
		 ::= { nbsStackInfo 7 }

	 nbsStackSpecSlotEntry OBJECT-TYPE
	 SYNTAX    NbsStackSpecSlotEntry
         ACCESS    not-accessible
         STATUS    mandatory
         DESCRIPTION
                 "An entry in the table, containing information
                  about a single Special Slot."
	 INDEX   { nbsStackSlotSpecNumber,
		   nbsStackSlotSpecUplNumber }
		 ::= { nbsStackSpecSlotTable 1 }

	 NbsStackSpecSlotEntry ::=
	 SEQUENCE   {
		     nbsStackSlotSpecNumber
                          INTEGER,
		     nbsStackSlotSpecUplNumber
                          INTEGER,
		     nbsStackSlotSpecUplRedundantMode
			  INTEGER,
		     nbsStackSlotSpecUplLeftLinkLed
			  INTEGER,
		     nbsStackSlotSpecUplLeftActivityLed
                          INTEGER,
		     nbsStackSlotSpecUplRightLinkLed
			  INTEGER,
		     nbsStackSlotSpecUplRightActivityLed
			  INTEGER,
		     nbsStackSlotSpecUplTestSemiAutoMode
			  INTEGER
		    }

	 nbsStackSlotSpecNumber	OBJECT-TYPE
         SYNTAX    INTEGER
         ACCESS    read-only
         STATUS    mandatory
         DESCRIPTION
		 "The Special Slot # in the Device."
		 ::= { nbsStackSpecSlotEntry 1 }
       
	 nbsStackSlotSpecUplNumber	OBJECT-TYPE
         SYNTAX    INTEGER
         ACCESS    read-only
         STATUS    mandatory
         DESCRIPTION
		 "The Uplink Module # in the
		  corresponding Special Slot in the Device."
		 ::= { nbsStackSpecSlotEntry 2 }
       
	 nbsStackSlotSpecUplRedundantMode	OBJECT-TYPE
         SYNTAX    INTEGER {
		       other                (1),
		       specialRedundant     (2),
		       autoRedundant        (3),
		       manualLeftRedundant  (4),
		       manualRightRedundant (5),
		       regularRedundant     (6),
		       masterLeftRedundant  (7),
		       masterRightRedundant (8)
		      }
	 ACCESS    read-write
         STATUS    mandatory
         DESCRIPTION
                 "Special Slot Additional Status:
                  other=(1) - unknown Status or Module is not Valid;

                  Redundant Modes used for the OptiSwitch Devices family:
		  'specialRedundant'(2) - Both connectors of the
                  GigaBit Redundant Module are connected to the same 2
                  connectors of the other GigaBit Redundant Module.
		  Module provides automatic quick Redundancy;
		  'autoRedundant'(3) - Each connector of the GigaBit
                  Redundant Module is connected to a Single GigaBit
                  Ethernet Module. Module provides automatic quick Redundancy;
		  'manualLeftRedundant'(4) - Each connector of the GigaBit
                  Redundant Module is connected to a Single GigaBit
                  Ethernet Module. Left Connector will be forced and
                  Right Connector will not be connected in any case.
                  'manualRightRedundant'(5) - Each connector of the GigaBit
                  Redundant Module is connected to a Single GigaBit
                  Ethernet Module. Right Connector will be forced and
                  Left Connector will not be connected in any case.
		  'semiAutoRedundant'(6) - Each connector of the GigaBit
                  Redundant Module is connected to a Single GigaBit
                  Ethernet Module. Module provides automatic Redundancy
                  from Primary Left Connector to the Right connector.
                  The difference is that to force back the Primary Left
                  connection the Test Operation [nbsStackSlotSpecUplTestSemiAutoMode]
                  has to be performed;

                  Redundant Modes used for the OptiSwitch Master Devices family:
                  'regularRedundant'(6) - The same as 'specialRedundant'(2)
                  and 'autoRedundant'(3). Provides automatic quick Redundancy.
                  'masterLeftRedundant'(7) - Provides automatic quick
                  Redundancy. The difference is that the module will always
                  force the Left Connection even when right Connection is OK. 
                  'masterRightRedundant'(8) - Provides automatic quick
                  Redundancy. The difference is that the module will always
                  force the Right Connection even when left Connection is OK."
		 ::= { nbsStackSpecSlotEntry 3 }

	 nbsStackSlotSpecUplLeftLinkLed	OBJECT-TYPE
	 SYNTAX    INTEGER {
		       other (1),
		       up    (2),
		       down  (3)
		      }
         ACCESS    read-only
	 STATUS    mandatory
         DESCRIPTION
		 "Rx Activity ower Left Connector in the Module."
		 ::= { nbsStackSpecSlotEntry 4 }

	 nbsStackSlotSpecUplLeftActivityLed	OBJECT-TYPE
	 SYNTAX    INTEGER {
		       other (1),
		       up    (2),
		       down  (3)
		      }
         ACCESS    read-only
	 STATUS    mandatory
         DESCRIPTION
		 "Tx Activity ower Left Connector in the Module."
		 ::= { nbsStackSpecSlotEntry 5 }

	 nbsStackSlotSpecUplRightLinkLed	OBJECT-TYPE
	 SYNTAX    INTEGER {
		       other (1),
		       up    (2),
		       down  (3)
		      }
         ACCESS    read-only
	 STATUS    mandatory
         DESCRIPTION
		 "Rx Activity ower Right Connector in the Module."
		 ::= { nbsStackSpecSlotEntry 6 }

	 nbsStackSlotSpecUplRightActivityLed	OBJECT-TYPE
	 SYNTAX    INTEGER {
		       other (1),
		       up    (2),
		       down  (3)
		      }
         ACCESS    read-only
	 STATUS    mandatory
         DESCRIPTION
		 "Tx Activity ower Right Connector in the Module."
		 ::= { nbsStackSpecSlotEntry 7 }

	 nbsStackSlotSpecUplTestSemiAutoMode	OBJECT-TYPE
	 SYNTAX    INTEGER {
		       readyForTest (1),
		       startTest    (2)
		      }
         ACCESS    read-write
	 STATUS    mandatory
         DESCRIPTION
		 "Used for the OptiSwitch Devices family to perform
                 Test Operation while Module is in 'semiAutoRedundant' Mode.
                 'readyForTest' (1) - used for SNMP GET operation only.
                 'startTest'    (2) - used for SNMP SET operation to initiate the Test."
		 ::= { nbsStackSpecSlotEntry 8 }

-- *************************************************************
-- Objects in the Multi Connectioned Ports Group
-- *************************************************************
        
nbsStackMultiConPortGroup    OBJECT IDENTIFIER ::= { nbsStackInfo 10}

-- *************************************************************
-- Objects in the Multi Connectioned Ports Table
-- *************************************************************
        
	 nbsStackMultiConPortTable OBJECT-TYPE
	 SYNTAX    SEQUENCE OF NbsStackMultiConPortEntry
         ACCESS    not-accessible
         STATUS    mandatory
         DESCRIPTION
                 "Table of descriptive and status information about
	          the multi connectivity Ports."
		 ::= { nbsStackMultiConPortGroup 5 }

	 nbsStackMultiConPortEntry OBJECT-TYPE
	 SYNTAX    NbsStackMultiConPortEntry
         ACCESS    not-accessible
         STATUS    mandatory
         DESCRIPTION
                 "An entry in the table, containing information
                  about a specific multi connectivity Port."
	 INDEX   { nbsStackMultiConPortId }
		 ::= { nbsStackMultiConPortTable 1 }

	 NbsStackMultiConPortEntry ::=
	 SEQUENCE   {
		     nbsStackMultiConPortId
                          INTEGER,
                     nbsStackMultiConPortConnectorsNumber
                          INTEGER,
                     nbsStackMultiConPortForceMode
                          INTEGER,
                     nbsStackMultiConPortForcedConnector
                          INTEGER
                    }

         nbsStackMultiConPortId  OBJECT-TYPE
         SYNTAX    INTEGER
         ACCESS    read-only
         STATUS    mandatory
         DESCRIPTION
		 "The Multi Connectivity Port Id in the Device.
                  The same as [ifIndex] in the MIB-II."
		 ::= { nbsStackMultiConPortEntry 1 }
       
	 nbsStackMultiConPortConnectorsNumber  OBJECT-TYPE
         SYNTAX    INTEGER
         ACCESS    read-only
         STATUS    mandatory
         DESCRIPTION
		 "The real Number of Connectors in the corresponding
		  Multi Connectivity Port in the Device."
		 ::= { nbsStackMultiConPortEntry 2 }

	 nbsStackMultiConPortForceMode	OBJECT-TYPE
	 SYNTAX    INTEGER {
		       other (1),
		       auto  (2),
		       force (3)
		      }
	 ACCESS    read-write
         STATUS    mandatory
         DESCRIPTION
                  "The Active Connector Forcing mode:
		  other=(1)  - Unknown mode;
		  auto=(2)   - System will choose automatically which
                               Connector in the Multi Connectivity Port 
                               will be forced;
		  force=(3)  - User will choose manually which
                               Connector in the Multi Connectivity Port 
                               will be forced. Number of Connector must be set
                               in the [nbsStackMultiConPortForcedConnector]"
		 ::= { nbsStackMultiConPortEntry 3 }

	 nbsStackMultiConPortForcedConnector  OBJECT-TYPE
         SYNTAX    INTEGER
         ACCESS    read-write
         STATUS    mandatory
         DESCRIPTION
		 "The Number of Connector that will be forced in the
                  corresponding Multi Connectivity Port in the Device.
                  (0 - in case of [nbsStackMultiConPortForceMode] = 'auto')"
		 ::= { nbsStackMultiConPortEntry 4 }

-- *************************************************************
-- Objects in the Multi Connectioned Port Connectors Table
-- *************************************************************
        
	 nbsStackMultiConPortConnectorTable OBJECT-TYPE
	 SYNTAX    SEQUENCE OF NbsStackMultiConPortConnectorEntry
         ACCESS    not-accessible
         STATUS    mandatory
         DESCRIPTION
                 "Table of descriptive and status information about
	          the multi connectivity Ports."
		 ::= { nbsStackMultiConPortGroup 7 }
                      
	 nbsStackMultiConPortConnectorEntry OBJECT-TYPE
	 SYNTAX    NbsStackMultiConPortConnectorEntry
         ACCESS    not-accessible
         STATUS    mandatory
         DESCRIPTION
                 "An entry in the table, containing information
                  about a specific multi connectivity Port."
	 INDEX   { nbsStackMultiConPortNumber,
		   nbsStackMultiConPortConnectorNumber }
		 ::= { nbsStackMultiConPortConnectorTable 1 }

	 NbsStackMultiConPortConnectorEntry ::=
	 SEQUENCE   {
		     nbsStackMultiConPortNumber
                          INTEGER,
		     nbsStackMultiConPortConnectorNumber
                          INTEGER,
		     nbsStackMultiConPortConnectorType
			  INTEGER,
		     nbsStackMultiConPortConnectorSubType
			  INTEGER,
		     nbsStackMultiConPortConnectorLinkStatus
			  INTEGER,
		     nbsStackMultiConPortConnectorRxLoss
			  INTEGER,
		     nbsStackMultiConPortConnectorTxFault
			  INTEGER
		    }

         nbsStackMultiConPortNumber  OBJECT-TYPE
         SYNTAX    INTEGER
         ACCESS    read-only
         STATUS    mandatory
         DESCRIPTION
		 "The Multi Connectivity Port # in the Device."
		 ::= { nbsStackMultiConPortConnectorEntry 1 }
       
	 nbsStackMultiConPortConnectorNumber  OBJECT-TYPE
         SYNTAX    INTEGER
         ACCESS    read-only
         STATUS    mandatory
         DESCRIPTION
		 "The Connector # in the
		  corresponding Multi Connectivity Port in the Device."
		 ::= { nbsStackMultiConPortConnectorEntry 2 }

	 nbsStackMultiConPortConnectorType  OBJECT-TYPE
         SYNTAX    INTEGER {
		       other       (1),
		       static      (2),
		       gbic        (3),
		       sfp         (4),
		       xfp         (5)
		      }
	 ACCESS    read-only
         STATUS    mandatory
         DESCRIPTION
		 "Multi Connectivity Port Connector Types:
		  other=(1)      - Unknown type of connector;
		  static=(2)     - Not Changeable type of connector;
		  gbic=(3)       - GBIC    type of connector;
		  sfp=(4)        - SFP     type of connector;
		  xfp=(5)        - XFP     type of connector;"
		 ::= { nbsStackMultiConPortConnectorEntry 3 }

	 nbsStackMultiConPortConnectorSubType  OBJECT-TYPE
         SYNTAX    INTEGER {
		       other       (1),
		       rj45        (2),
		       sc          (3),
		       lc          (4),
		       mtrj        (5),
		       vf          (6)
		      }
	 ACCESS    read-only
         STATUS    mandatory
         DESCRIPTION
		 "Multi Connectivity Port Connector Physical Sub Type:
		  other=(1)      - Unknown or N/A Connector's connectivity Type;
		  rj45=(2)       - Copper RJ45;
		  sc=(3)         - Regular Fibre Optic [FO];
		  lc=(4)         - LC;
		  mtrj=(5)       - MTRJ;
		  vf=(6)         - VF"
		 ::= { nbsStackMultiConPortConnectorEntry 4 }

	 nbsStackMultiConPortConnectorLinkStatus  OBJECT-TYPE
         SYNTAX    INTEGER {
		       other       (1),
		       notLinked   (2),
		       linked      (3),
		       errorState  (4),
                       blocked     (5)
		      }
	 ACCESS    read-only
         STATUS    mandatory
         DESCRIPTION
		 "Multi Connectivity Uplink Connector's Link Status:
		  other=(1)      - Unknown connector's Link status;
		  notLinked=(2)  - Connector's Link is down;
		  linked=(3)  	 - Connector's Link is up;
		  errorState=(4) - Error Connector's Link status;
		  blocked=(5)    - Connector's Link status is blocked;"
		 ::= { nbsStackMultiConPortConnectorEntry 5 }

	 nbsStackMultiConPortConnectorRxLoss  OBJECT-TYPE
         SYNTAX    INTEGER {
		       other       (1),
		       ok          (2),
		       loss        (3)
		      }
	 ACCESS    read-only
         STATUS    mandatory
         DESCRIPTION
		 "Multi Connectivity Uplink Connector's Rx Loss Status:
		  other=(1)      - Unknown connector's Rx Loss status;
		  ok=(2)         - Connector's Rx Loss not exists;
		  loss=(3)  	 - Connector's Rx Loss exists"
		 ::= { nbsStackMultiConPortConnectorEntry 6 }

	 nbsStackMultiConPortConnectorTxFault  OBJECT-TYPE
         SYNTAX    INTEGER {
		       other       (1),
		       ok          (2),
		       fault       (3)
		      }
	 ACCESS    read-only
         STATUS    mandatory
         DESCRIPTION
		 "Multi Connectivity Uplink Connector's Link Status:
		  other=(1)      - Unknown connector's Tx Fault status;
		  ok=(2)         - Connector's Tx Fault not exists;
		  fault=(3)  	 - Connector's Tx Fault exists"
		 ::= { nbsStackMultiConPortConnectorEntry 7 }


-- *************************************************************
-- Objects in the Virtual Cable Diagnostics Group
-- *************************************************************
        
nbsStackVcdGroup    OBJECT IDENTIFIER ::= { nbsStackInfo 12}

-- *************************************************************
-- Objects in the Ports Virtual Cable Diagnostics Table
-- *************************************************************
        
        nbsStackVcdGenSupport OBJECT-TYPE
        SYNTAX  INTEGER {
            notSupported (1),
            supported    (2)
        }       
        ACCESS  read-only
        STATUS  mandatory
        DESCRIPTION
                 "Virtual Cable Diagnostics feature support (per Device)."
                 ::= { nbsStackVcdGroup 1 }

	 nbsStackVcdPortTable OBJECT-TYPE
	 SYNTAX    SEQUENCE OF NbsStackVcdPortEntry
         ACCESS    not-accessible
         STATUS    mandatory
         DESCRIPTION
                 "Table of status information about
	          a Port's Virtual Cable Diagnostics."
		 ::= { nbsStackVcdGroup 2 }

	 nbsStackVcdPortEntry OBJECT-TYPE
	 SYNTAX    NbsStackVcdPortEntry
         ACCESS    not-accessible
         STATUS    mandatory
         DESCRIPTION
                 "An entry in the table, containing status information
                  about a Port's Virtual Cable Diagnostics."
	 INDEX   { nbsStackVcdPortId }
		 ::= { nbsStackVcdPortTable 1 }

	 NbsStackVcdPortEntry ::=
	 SEQUENCE   {
		     nbsStackVcdPortId
                          INTEGER,
                     nbsStackVcdPortTestRun
                          INTEGER,
                     nbsStackVcdPortPair12Distance
                          INTEGER,
                     nbsStackVcdPortPair12TestStatus
                          INTEGER,
                     nbsStackVcdPortPair36Distance
                          INTEGER,
                     nbsStackVcdPortPair36TestStatus
                          INTEGER,
                     nbsStackVcdPortPair45Distance
                          INTEGER,
                     nbsStackVcdPortPair45TestStatus
                          INTEGER,
                     nbsStackVcdPortPair78Distance
                          INTEGER,
                     nbsStackVcdPortPair78TestStatus
                          INTEGER,
                     nbsStackVcdPortSupport
                          INTEGER,
                     nbsStackVcdPortTestTime
                          TimeTicks
                    }

         nbsStackVcdPortId  OBJECT-TYPE
         SYNTAX    INTEGER
         ACCESS    read-only
         STATUS    mandatory
         DESCRIPTION
		 "The Port Id supported VCD feature in the Device.
                  The same as [ifIndex] in the MIB-II."
		 ::= { nbsStackVcdPortEntry 1 }
       
	 nbsStackVcdPortTestRun  OBJECT-TYPE
	 SYNTAX    INTEGER {
		       startVcdTest              (1),
		       testIsRunning             (2),
		       vcdTestCompletedOk        (3),
		       vcdTestCompletedWithError (4),
		       vcdNotTested              (5)
                      }
         ACCESS    read-write
         STATUS    mandatory
         DESCRIPTION
                 "The Port VCD Test mode:
                  startVcdTest=(1)    - used for SNMP SET operation
                                        to run VCD Test; 
                  testIsRunning=(2)   - used for SNMP GET operation
                                        to show that VCD Test is still
                                        not completed;
                  vcdTestCompletedOk=(3)- used for SNMP GET operation
                                        to show that VCD Test is already
                                        completed with no Error.
                  vcdTestCompletedWithError=(4)- used for SNMP GET operation
                                        to show that VCD Test is already
                                        completed with some Error.
                  vcdNotTested=(5)      - used for SNMP GET operation
                                        to show that VCD Test has not yet been executed."
		 ::= { nbsStackVcdPortEntry 2 }

	 nbsStackVcdPortPair12Distance  OBJECT-TYPE
         SYNTAX    INTEGER
         ACCESS    read-only
         STATUS    mandatory
         DESCRIPTION
		 "The distance [in CM] to the Problem found with help
                  of VCD test into the Pair of Wires 1 and 2."
		 ::= { nbsStackVcdPortEntry 3 }

	 nbsStackVcdPortPair12TestStatus  OBJECT-TYPE
	 SYNTAX    INTEGER {
		       other             (1),
		       good              (2),
		       testFail          (3),
		       impedanceMismatch (4),
		       openCable         (5),
		       shortCable        (6)
		      }
	 ACCESS    read-only
         STATUS    mandatory
         DESCRIPTION
                  "The VCD Test result for Pair of Wires 1 and 2 :
		  other=(1)   - unknown;
		  good=(2)    - the Cable is OK (no problem found);
		  testFail=(3)- the VCD Test was failed for some reason;
		  impedanceMismatch=(3)- the VCD Test found the impedance
                                problems in the Wires;
                  openCable=(5)-the VCD Test found the break in the Wire;
                  openCable=(6)-the VCD Test found the short circuit in
                                the Wire."
		 ::= { nbsStackVcdPortEntry 4 }

	 nbsStackVcdPortPair36Distance  OBJECT-TYPE
         SYNTAX    INTEGER
         ACCESS    read-only
         STATUS    mandatory
         DESCRIPTION
		 "The distance [in CM] to the Problem found with help
                  of VCD test into the Pair of Wires 3 and 6."
		 ::= { nbsStackVcdPortEntry 5 }

	 nbsStackVcdPortPair36TestStatus  OBJECT-TYPE
	 SYNTAX    INTEGER {
		       other             (1),
		       good              (2),
		       testFail          (3),
		       impedanceMismatch (4),
		       openCable         (5),
		       shortCable        (6)
		      }
	 ACCESS    read-only
         STATUS    mandatory
         DESCRIPTION
                  "The VCD Test result for Pair of Wires 3 and 6 :
		  other=(1)   - unknown;
		  good=(2)    - the Cable is OK (no problem found);
		  testFail=(3)- the VCD Test was failed for some reason;
		  impedanceMismatch=(3)- the VCD Test found the impedance
                                problems in the Wires;
                  openCable=(5)-the VCD Test found the break in the Wire;
                  openCable=(6)-the VCD Test found the short circuit in
                                the Wire."
		 ::= { nbsStackVcdPortEntry 6 }

	 nbsStackVcdPortPair45Distance  OBJECT-TYPE
         SYNTAX    INTEGER
         ACCESS    read-only
         STATUS    mandatory
         DESCRIPTION
		 "The distance [in CM] to the Problem found with help
                  of VCD test into the Pair of Wires 4 and 5."
		 ::= { nbsStackVcdPortEntry 7 }

	 nbsStackVcdPortPair45TestStatus  OBJECT-TYPE
	 SYNTAX    INTEGER {
		       other             (1),
		       good              (2),
		       testFail          (3),
		       impedanceMismatch (4),
		       openCable         (5),
		       shortCable        (6)
		      }
	 ACCESS    read-only
         STATUS    mandatory
         DESCRIPTION
                  "The VCD Test result for Pair of Wires 4 and 5 :
		  other=(1)   - unknown;
		  good=(2)    - the Cable is OK (no problem found);
		  testFail=(3)- the VCD Test was failed for some reason;
		  impedanceMismatch=(3)- the VCD Test found the impedance
                                problems in the Wires;
                  openCable=(5)-the VCD Test found the break in the Wire;
                  openCable=(6)-the VCD Test found the short circuit in
                                the Wire."
		 ::= { nbsStackVcdPortEntry 8 }

	 nbsStackVcdPortPair78Distance  OBJECT-TYPE
         SYNTAX    INTEGER
         ACCESS    read-only
         STATUS    mandatory
         DESCRIPTION
		 "The distance [in CM] to the Problem found with help
                  of VCD test into the Pair of Wires 7 and 8."
		 ::= { nbsStackVcdPortEntry 9 }

	 nbsStackVcdPortPair78TestStatus  OBJECT-TYPE
	 SYNTAX    INTEGER {
		       other             (1),
		       good              (2),
		       testFail          (3),
		       impedanceMismatch (4),
		       openCable         (5),
		       shortCable        (6)
		      }
	 ACCESS    read-only
         STATUS    mandatory
         DESCRIPTION
                 "The VCD Test result for Pair of Wires 7 and 8 :
		  other=(1)   - unknown;
		  good=(2)    - the Cable is OK (no problem found);
		  testFail=(3)- the VCD Test was failed for some reason;
		  impedanceMismatch=(3)- the VCD Test found the impedance
                                problems in the Wires;
                  openCable=(5)-the VCD Test found the break in the Wire;
                  openCable=(6)-the VCD Test found the short circuit in
                                the Wire."
		 ::= { nbsStackVcdPortEntry 10 }

         nbsStackVcdPortSupport  OBJECT-TYPE
         SYNTAX  INTEGER {
                       notSupported (1),
                       supported    (2),
                       unknown      (3)
                      }
         ACCESS  read-only
         STATUS  mandatory
         DESCRIPTION
                 "Virtual Cable Diagnostics feature support (per Port)."
                 ::= { nbsStackVcdPortEntry 11 }

         nbsStackVcdPortTestTime  OBJECT-TYPE
         SYNTAX      TimeTicks
         MAX-ACCESS  read-only
         STATUS      current
         DESCRIPTION
                 "The value of sysUpTime at the time of the last creation or
                 deletion of an entry in the ifTable.  If the number of
                 entries has been unchanged since the last re-initialization
                 of the local network management subsystem, then this object
                 contains a zero value."
                 ::= { nbsStackVcdPortEntry 12 }

------------------------------------------------------------------------------
-- TRAPS
------------------------------------------------------------------------------
 
 	specSlotLinkChanged TRAP-TYPE
    	ENTERPRISE 	nbsStackInfo
    	VARIABLES {
                    nbsStackSlotSpecNumber
                  }
    	DESCRIPTION
    		"The SNMP trap that is generated when 
    		 Link status was changed on the GER Module."
              ::= 22
    
END
